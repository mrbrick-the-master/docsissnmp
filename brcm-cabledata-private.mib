--****************************************************************************
--
-- Copyright (c) 2002-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cabledata-private.mib
--    Author:   Kevin O'Neal
--    Creation Date: 4-june-2002
--
--****************************************************************************
--    Description:
--
--		private MIB for cableData products
--		
--****************************************************************************
--    Revision History:
--
--****************************************************************************

BRCM-CABLEDATA-PRIVATE-MIB DEFINITIONS ::= BEGIN

IMPORTS
    MODULE-IDENTITY,
    OBJECT-TYPE,
    Integer32
        FROM SNMPv2-SMI
    RowStatus
        FROM SNMPv2-TC
    cableDataPrivate
        FROM BRCM-CABLEDATA-SMI;
                
cableDataPrivateMIB MODULE-IDENTITY
    LAST-UPDATED "201407290000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB which defines a root node for the 'private'
         branch of the MIB tree.  This branch is only accessible in factory
         and engineering configurations and is not intended for runtime use.
         
         This MIB also provides a mechanism for entering factory or engineering
         modes and for securing the mechanism."
    REVISION      "201407290000Z"
    DESCRIPTION
        "Fixed copyright header date."
    REVISION      "200702050000Z"
    DESCRIPTION
        "Module description was updated. 
         Compilability issues were cleaned up: 
         - Range restriction was added to object cdPvtMibEnableKeyIndex."
    REVISION      "200206040000Z"
    DESCRIPTION
        "Initial version of this MIB module."
    ::= { cableDataPrivate 1 }
        
cableDataPrivateMIBObjects OBJECT IDENTIFIER ::= { cableDataPrivateMIB 1}

cableDataPrivateBase OBJECT IDENTIFIER ::= { cableDataPrivateMIBObjects 1 }
        
cdPrivateMibEnable OBJECT-TYPE
    SYNTAX      INTEGER {
                disabled(0),
                factory(1),
                engineering(2)
    }
    MAX-ACCESS  read-write
    STATUS      current
    DESCRIPTION
       "Setting this object to disabled(0) causes the entire cableDataPrivate 
        branch of the MIB to permanently disappear.  Once all private 
        operations are complete, this object should be set to disabled(0).  
        Setting this object to factory(1) will expose the 
        cableDataPrivateFactory branch, but will hide the 
        cableDataPrivateEngineering branch.  Setting this object to 
        engineering(2) will expose the cableDataPrivateEngineering branch
        in addition to the cableDataPrivateFactory branch.  Initial value for 
        this object is factory(1)."
    ::= { cableDataPrivateBase 1 }
    
cdPrivateMibEnableKeyTable  OBJECT-TYPE
    SYNTAX      SEQUENCE OF CdPrivateMibEnableKeyEntry
    MAX-ACCESS  not-accessible
    STATUS      current
    DESCRIPTION
        "A table which may be used to re-enable the private MIB after
         privateMibEnable is set to false.  This table contains a list
         of keys, all of which must be set to their current values in a single
         SNMP-SET PDU in order to set privateMibEnable back to manufacturing.
         If the table is empty, then this mechanism is disabled and the private
         MIB cannot be re-enabled.  The number of keys required to re-enable
         the private MIB is controlled at configuration time by the number of
         entries created in the table.  Although there is no theoretical
         maximum to the number of keys which may be required, a particular
         device is likely to have non-volatile storage constraints which
         will limit the maximum number of entries.  If an attempt is made to
         create more rows than the device can support, an error code of
         NO CREATION will be returned."
    ::= { cableDataPrivateBase 2 }

cdPrivateMibEnableKeyEntry OBJECT-TYPE
    SYNTAX      CdPrivateMibEnableKeyEntry
    MAX-ACCESS  not-accessible
    STATUS      current
    DESCRIPTION
        "An entry identifying a single key value used to re-enable the private
         MIB once it has been disabled."
    INDEX   { cdPvtMibEnableKeyIndex }
    ::= { cdPrivateMibEnableKeyTable 1 }

CdPrivateMibEnableKeyEntry ::= 
    SEQUENCE    {
                cdPvtMibEnableKeyIndex          Integer32,
                cdPvtMibEnableKeyValue          OCTET STRING,
                cdPvtMibEnableKeyStatus         RowStatus
    }
    
cdPvtMibEnableKeyIndex OBJECT-TYPE
    SYNTAX      Integer32 (1..8)
    MAX-ACCESS  not-accessible
    STATUS      current
    DESCRIPTION
        "A unique value used to identify this key instance.  Note that the
         indices need not be sequential, although they must be positive.
         Also note that a particular device may have non-volatile storage
         constraints which limit the value of this object.  If an attempt is
         made to create a row which has an index that is not valid for the
         particular device, an error code of NO CREATION will be returned."
    ::= { cdPrivateMibEnableKeyEntry 1 }
    
cdPvtMibEnableKeyValue OBJECT-TYPE
    SYNTAX      OCTET STRING
    MAX-ACCESS  read-create
    STATUS      current
    DESCRIPTION
        "A value used to control re-enabling of the private MIB once it has
         been disabled.  If the private MIB is disabled, the only value which
         may be successfully set to this object is its current value.  If the
         MIB is enabled, then this value may be set to any value in order to
         configure the table.  Note that there is no theoretical limit to the
         size of this string, although a particular device is likely to have
         non-volatile storage constraints which will limit the size of the
         value.  If an attempt is made to set this value to too large of a 
         string, an error code of WRONG LENGTH will be returned.  Also note 
         that this value may contain hex values as well as ASCII printable 
         ones."
    DEFVAL { "" }
    ::= { cdPrivateMibEnableKeyEntry 2 }
    
cdPvtMibEnableKeyStatus OBJECT-TYPE
    SYNTAX      RowStatus
    MAX-ACCESS  read-create
    STATUS      current
    DESCRIPTION
        "Controls and reflects the status of rows in this table. Rows in this 
         table may be created by either the create-and-go or create-and-wait 
         paradigms.  There is no restriction on changing values in a row of 
         this table while the row is active.  Setting the value of this object 
         to active (either directly or indirectly via create-and-go) will cause 
         the row to be written to non-volatile storage.  Changing the value of
         cdPrivateEnableKeyValue while the row is active will also cause the
         row to be written to non-volatile storage."
    ::= { cdPrivateMibEnableKeyEntry 3 }
    
    
-- 
-- cableDataFactory OBJECT IDENTIFIER ::= { cdPrivateMibObjects 2 }
-- see BRCM-CABLEDATA-FACTORY-MIB
--

-- 
-- cableDataEngineering OBJECT IDENTIFIER ::= { cdPrivateMibObjects 3 }
-- see BRCM-CABLEDATA-ENGINEERING-MIB
--

END
