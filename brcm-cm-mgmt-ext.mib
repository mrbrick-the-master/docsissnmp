--****************************************************************************
--
-- Copyright (c) 2005-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cm-mgmt-ext.mib
--    Author:   Kevin O'Neal
--    Creation Date: April 18, 2005
--
--****************************************************************************
--    Description:
--
--		private MIB for runtime (not factory) CM management
--		
--****************************************************************************
--    Revision History:
--
--****************************************************************************

BRCM-CM-MGMT-EXT-MIB DEFINITIONS ::= BEGIN

IMPORTS
    MODULE-IDENTITY,
    OBJECT-TYPE,
    Integer32
        FROM SNMPv2-SMI
    broadcomCableDataMgmt
        FROM BRCM-CABLEDATA-MGMT-MIB;
                
cmMgmtExt MODULE-IDENTITY
    LAST-UPDATED "201401080000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom CM management extension MIB.  This MIB is supported only for 
         products implementing the Broadcom CM vendor extension."
    REVISION      "201401080000Z"
    DESCRIPTION
        "Corrected Last-Updated, Revision and Description fields."
    REVISION      "201011300000Z"
    DESCRIPTION
        "Cleaned up range restriction and description clause for
         cmScanPushFrequency."
    REVISION      "200702050000Z"
    DESCRIPTION
        "Range restrictions for objects cmScanPushFrequency and cmScanIndex 
         were adjusted.
         Compilability issues were cleaned up: 
         - Missing imports were added."
    REVISION      "200504180000Z"
    DESCRIPTION
            "Initial version of this MIB module."
    ::= { broadcomCableDataMgmt 2 }
    
cmMgmtExtBase OBJECT IDENTIFIER ::= { cmMgmtExt 1 }
    
cmMgmtExtScan OBJECT IDENTIFIER ::= { cmMgmtExt 2 }

cmScanPushFrequency OBJECT-TYPE
    SYNTAX      Integer32 (0..1000000000)
    UNITS       "hertz"
    MAX-ACCESS  read-write
    STATUS      current
    DESCRIPTION
        "Setting this object will add a new entry to the cmScanTable.  The new
         entry will have a cmScanFrequency value equal to the value set to
         this object.  The index (cmScanIndex) of the new entry will be 1.  
         Any existing entries will be re-indexed starting at 2.  If the table is 
         full, the last entry in the table will be dropped.  If the value set 
         here already exists in the table, it will be moved from its current 
         position in the table to become entry 1 (a duplicate entry will not be 
         added).   Setting this object to a value of 0  will flush the 
         cmScanTable.  When read, this object always returns 0."
    ::= { cmMgmtExtScan 1 }

cmScanTable  OBJECT-TYPE
    SYNTAX      SEQUENCE OF CmScanEntry
    MAX-ACCESS  not-accessible
    STATUS      current
    DESCRIPTION
        "A table of the most recent known good frequencies to which the CM
         has registered.  The most recent good frequency will be at index
         1, with subsequent entries being in chronological order from newest
         to oldest.  Note that the table will not grow unbounded.  Once the
         maximum number of entries is reached, the oldest entries will be
         discarded."
    ::= { cmMgmtExtScan 2 }
    
cmScanEntry OBJECT-TYPE
    SYNTAX      CmScanEntry
    MAX-ACCESS  not-accessible
    STATUS      current
    DESCRIPTION
        "An entry which identifies a downstream frequency to which the CM has
         recently successfully registered."
    INDEX   { cmScanIndex }
    ::= { cmScanTable 1 }
    
CmScanEntry ::= 
    SEQUENCE    {
                cmScanIndex     Integer32,
                cmScanFrequency Integer32
    }
    
cmScanIndex OBJECT-TYPE
    SYNTAX      Integer32 (1..128)
    MAX-ACCESS  not-accessible
    STATUS      current
    DESCRIPTION
        "Identifies the instance of this scan entry."
    ::= { cmScanEntry 1 }

cmScanFrequency OBJECT-TYPE
    SYNTAX      Integer32
    UNITS       "hertz"
    MAX-ACCESS  read-only
    STATUS      current
    DESCRIPTION
        "A downstream frequency to which the CM has recently successfully 
         registered, or which has been provisioned by way of a set to
         cmScanPushFrequency."
    REFERENCE 
         "docsIfDownChannelFrequency from DOCS-IF-MIB" 
    ::= { cmScanEntry 2 }
    
     
cmMgmtExtBaseStandbySwitchStatus OBJECT-TYPE
    SYNTAX      INTEGER {						
                on(1),
                off(2)
    }
    MAX-ACCESS  read-write
    STATUS      current
    DESCRIPTION
        "Reports/Sets the position of the standby switch. 
          
         A GET on this object returns the current state of the standby switch.
         
         A SET to a value of 'on(1)'  enables standby mode for the device.
         A SET to a value of 'off(2)' disables standby mode for the device.
	  
         When standby-mode is enabled 'on(1)', the device blocks WAN data traffic
         to/from the CPEs."  
    ::= { cmMgmtExtBase 1 }

        
END
