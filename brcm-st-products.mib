-- **************************************************************************
-- 
-- Copyright (c) 2006-2014 Broadcom Corporation
-- 
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.
-- 
-- Except as expressly set forth in the Authorized License,
--                                                                          
-- 1.     This program, including its structure, sequence and organization,
-- constitutes the valuable trade secrets of Broadcom, and you shall use all
-- reasonable efforts to protect the confidentiality thereof, and to use this
-- information only in connection with your use of Broadcom integrated circuit
-- products.
--                                                                          
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--                                                                          
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--                                                                          
--**************************************************************************
--    Revision History:
--
--**************************************************************************

BRCM-ST-PRODUCTS-MIB DEFINITIONS ::= BEGIN

IMPORTS
    MODULE-IDENTITY
        FROM SNMPv2-SMI
    AGENT-CAPABILITIES 
        FROM SNMPv2-CONF
    cableDataProducts 
        FROM BRCM-CABLEDATA-SMI;

brcmStProducts MODULE-IDENTITY
    LAST-UPDATED "201406240000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata management MIB"
    REVISION      "201406240000Z"
    DESCRIPTION
            "Fixed dates."
    REVISION      "200612200000Z"
    DESCRIPTION
            "Initial version of this MIB module."
    ::= { cableDataProducts 3 }
    
--
-- Product IDs for Broadcom SetTop reference designs.
-- We use the convention of brcmStProducts.chip for our reference design
-- sysObjectID values.  This is obviously not a solution which extends to
-- real-world products since there could well be many products based on a
-- given chipset.  However, for our internal purposes it is sufficient.
-- New products will be added to this list as new chipsets become available.
-- 

-- stReferenceDesigns = 1.3.6.1.4.1.4413.2.1.3.1
stReferenceDesigns OBJECT IDENTIFIER ::= { brcmStProducts 1 }

bcm97455 OBJECT IDENTIFIER ::= { stReferenceDesigns 97455 }


--
-- Processor IDs for Broadcom processors used in SetTop designs.
-- We use the convention of brcmStProcessors.chip. These OIDs
-- are appropriate for use in describing the processor in the
-- HOST_RESOURCES MIB.
-- 

-- stProcessors = 1.3.6.1.4.1.4413.2.1.3.2
stProcessors OBJECT IDENTIFIER ::= { brcmStProducts 2 }

bcm97401 OBJECT IDENTIFIER ::= { stProcessors 97401 }



END
