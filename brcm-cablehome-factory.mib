--****************************************************************************
--                                                                          
-- Copyright (c) 2002-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cablehome-factory.mib
--    Author:   Kevin O'Neal
--    Creation Date: 23-august-2002
--
--**************************************************************************
--    Description:
--
--		private MIB for cablemodem factory
--		
--**************************************************************************
--    Revision History:
--
--**************************************************************************

BRCM-CABLEHOME-FACTORY-MIB DEFINITIONS ::= BEGIN

IMPORTS
    MODULE-IDENTITY,
    OBJECT-TYPE
        FROM SNMPv2-SMI
    cableDataFactory
        FROM BRCM-CABLEDATA-FACTORY-MIB;
                
cableHomeFactory MODULE-IDENTITY
    LAST-UPDATED "201401080000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for management and configuration
         of objects used in manufacturing of CableHome devices."
    REVISION      "201401080000Z"
    DESCRIPTION
        "Corrected Last-Updated, Revision and Description fields."
    REVISION      "200702050000Z"
    DESCRIPTION
        "Module description was updated. 
         Compilability issues were cleaned up: 
         - Chronological order of revision history was corrected."    
    REVISION      "200404270000Z"
    DESCRIPTION
        "Added objects chSpsClabCvcRootCaCert and chSpsClabCvcCaCert."
    REVISION      "200403240000Z"
    DESCRIPTION
        "Changed behavior of chSecPsPrivateKey to return a CRC32 of the
         key when read rather than the key itself for security reasons."    
    REVISION      "200208230000Z"
    DESCRIPTION
        "Initial version of this MIB module."
    ::= { cableDataFactory 3 }

-- chFactoryBase: miscellaneous control/state objects for factory mode    
chFactoryBase OBJECT IDENTIFIER ::= { cableHomeFactory 1 }

-- chFactorySecurity: Security-related factory objects
chFactorySecurity OBJECT IDENTIFIER ::= { cableHomeFactory 2 }

chSecPsCert OBJECT-TYPE
    SYNTAX      OCTET STRING -- size?
    MAX-ACCESS  read-write
    STATUS      current
    DESCRIPTION
        "The CableHome PS Element Certificate."
    ::= { chFactorySecurity 1 }
    
chSecPsPrivateKey OBJECT-TYPE
    SYNTAX      OCTET STRING -- size?
    MAX-ACCESS  read-write
    STATUS      current
    DESCRIPTION
        "The CableHome PS Element private key.  In order to prevent
         unauthorized discovery of the private key, when read this object
         does not return the key.  Instead, a CRC32 is performed over the
         key and the resulting 32 bit value is returned as a 4 byte octet
         string.  Note that if the key is empty, a CRC value of 00 00 00 00
         is returned."
    ::= { chFactorySecurity 2 }
    
chSecManCaCert OBJECT-TYPE
    SYNTAX      OCTET STRING -- size?
    MAX-ACCESS  read-write
    STATUS      current
    DESCRIPTION
        "The CableHome Manufacturer CA Certificate."
    ::= { chFactorySecurity 3 }
    
chSecSvcProviderRootCaCert OBJECT-TYPE
    SYNTAX      OCTET STRING -- size?
    MAX-ACCESS  read-write
    STATUS      current
    DESCRIPTION
        "The CableHome Service Provider Root CA Certificate."
    ::= { chFactorySecurity 4 }
    
-- Security objects present only for standalone PS (SPS)
-- Embedded (EPS) systems will not support these objects.
    
chSpsClabCvcRootCaCert OBJECT-TYPE
    SYNTAX      OCTET STRING
    MAX-ACCESS  read-write
    STATUS      current
    DESCRIPTION
        "The CableLabs CVC Root CA Certificate for SPS applications.  Note that
         this object is not present in embedded (EPS) devices."
    ::= { chFactorySecurity 5 }
    
chSpsClabCvcCaCert OBJECT-TYPE
    SYNTAX      OCTET STRING
    MAX-ACCESS  read-write
    STATUS      current
    DESCRIPTION
        "The CableLabs CVC CA Certificate for SPS applications.  Note that
         this object is not present in embedded (EPS) devices."
    ::= { chFactorySecurity 6 }
   
    
END
