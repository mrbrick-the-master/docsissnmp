--**************************************************************************
--                                                                          
--    Copyright 2010 Cisco Systems Inc.                                  
--    All Rights Reserved                                                   
--    No portions of this material may be reproduced in any
--    form without the written permission of:                                                
--             Cisco Systems Inc.                                         
--             5030 Sugarloaf Pkwy                                     
--             Lawrenceville, Georgia 30044                                    
--                                                                          
--**************************************************************************

SA-BATTERY-MIB DEFINITIONS ::= BEGIN
IMPORTS
        DateAndTime,
        TruthValue,
        DisplayString
                FROM SNMPv2-TC
        MODULE-IDENTITY, 
        OBJECT-TYPE,enterprises, 
        Integer32,IpAddress
                FROM SNMPv2-SMI
        ifIndex
                FROM IF-MIB;
                
sa           OBJECT IDENTIFIER ::= { enterprises 1429 }
saVoip       OBJECT IDENTIFIER ::= { sa 78 }

saBattery MODULE-IDENTITY
        LAST-UPDATED    "200903270000Z"
        ORGANIZATION    "Scientific Atlanta, A Cisco Company"
        CONTACT-INFO    "marcin.godlewski@sciatl.com"
        DESCRIPTION
            "MTA Battery status."

        -- History                        
        REVISION     "200903270000Z"
        DESCRIPTION
            "Added saBatterySerialNumber and saBatteryDateCode(CR-3683)"

        REVISION     "200711160000Z"
        DESCRIPTION
            "Added saBatteryIfOperationTable (1950)"

        REVISION     "200708140000Z"
        DESCRIPTION
            "Changed UNITS to percent for saBatteryReplacePercentage (1665)"

        REVISION     "200702070000Z"
        DESCRIPTION
            "Changed description for saMtaBatteryEndPntRingPower
             Removed DEVFAL and changed description for saMtaBatteryEndPntPower"

        REVISION     "200608110000Z"
        DESCRIPTION
            "Added saBatteryType (867)
             Changed OID for saBatteryHsdPower (867)
             Changed OID for saBatteryRfAmpPower (867)
             Added saBatteryCurrentStateA (356)
             Added saBatteryCurrentStateB (356)"

        ::= { saVoip 2 }
        

saBatteryAcFail OBJECT-TYPE
    SYNTAX INTEGER {
          false(0),
          true(1)
        }
    MAX-ACCESS 	  read-only
    STATUS        current
    DESCRIPTION	
        "Show the Battery AC status(AC_STATUS):
         0: AC Restored,
         1: AC Fail "
    ::= { saBattery 1 }

saBatteryReplace OBJECT-TYPE
    SYNTAX INTEGER {
          false(0),
          true(1)
        }
    MAX-ACCESS 	  read-only
    STATUS        current
    DESCRIPTION	
        "Show the Battery life status(BATTERY_STATUS):
         0: Battery Good,
         1: Replace Battery "
    ::= { saBattery 2 }

saBatteryMissing OBJECT-TYPE
    SYNTAX INTEGER {
          false(0),
          true(1)
        }
    MAX-ACCESS 	  read-only
    STATUS        current
    DESCRIPTION	
        "Show the Battery presence status(BATTERY_EXIST):
         0: Battery Present,
         1: Battery Missing "
    ::= { saBattery 3 }

saBatteryLow OBJECT-TYPE
    SYNTAX INTEGER {
          false(0),
	  true(1)
        }
    MAX-ACCESS 	  read-only
    STATUS        current
    DESCRIPTION	
        "Show the Battery charge status(BATTERY_ENERGY):
         0: Battery Not Low,
         1: Battery Low "
    ::= { saBattery 4 }

saBatteryTrapServer OBJECT-TYPE
    SYNTAX  IpAddress
    MAX-ACCESS 	  read-write
    STATUS        current
    DESCRIPTION	
        "The IP address of the host receiving SNMP traps."
    ::= { saBattery 5 }

saBatteryTrapControl OBJECT-TYPE
    SYNTAX BITS {
          acFailTrue (0),
          acFailFalse(1),
          replaceBatteryTrue (2),
          replaceBatteryFalse (3),
          batteryMissingTrue (4),
          batteryMissingFalse (5),
          batteryLowTrue (6),
          batteryLowFalse (7)
        }
    MAX-ACCESS 	  read-write
    STATUS        current
    DESCRIPTION	
        "Controls sending battery event change traps:
         bit 0 set: send trap if saBatteryAcFail changes from false(0) to true(1)
         bit 1 set: send trap if saBatteryAcFail changes from true(1) to false(0)
         bit 2 set: send trap if saBatteryReplace changes from false(0) to true(1)
         bit 3 set: send trap if saBatteryReplace changes from true(1) to false(0)
         bit 4 set: send trap if saBatteryMissing changes from false(0) to true(1)
         bit 5 set: send trap if saBatteryMissing changes from true(1) to false(0)
         bit 6 set: send trap if saBatteryLow changes from false(0) to true(1)
         bit 7 set: send trap if saBatteryLow changes from true(1) to false(0)"
    ::= { saBattery 6 }

saBatteryType OBJECT-TYPE
    SYNTAX INTEGER {
        dpx2203(0),
        dpx2203c(1)
        }
    MAX-ACCESS    read-only
    STATUS        current
    DESCRIPTION 
        "1 = old DPX2203 battery,
         2 = DPX2203c cartridge"
    ::= { saBattery 7 }

saBatteryHsdPower OBJECT-TYPE
    SYNTAX INTEGER {
        enable(0),
        disable(1)
    }
    MAX-ACCESS  read-write
    STATUS      current
    DESCRIPTION
        "Enable/Disable the CPE function operating in battery mode.
         0: Support Ethernet and USB data transfer when the EMTA is operating from battery power.
         1: Disable Ethernet and USB data transfer when the EMTA is operating from battery power.
            Note:  Mode=1: disable hardware for Ethernet and USB."
    DEFVAL { 1 }
    ::= { saBattery 8 }
       
saBatteryCpuPower OBJECT-TYPE
    SYNTAX INTEGER {
        true(0),
        false(1)
    }
    MAX-ACCESS  read-write
    STATUS      current
    DESCRIPTION
        "CPU runs under normal/lower clock rate operating in battery mode.
         0: Always keep CPU in normal power mode
         1: operate main CPU in low power mode when the CPU is not in use and the EMTA is operating
            from battery power.
         Note:  Mode=1: use 50 MHz and CPU Halt mode if on phone call in progress and no packet traffic
         on battery power, else using 200 MHz CPU."
    DEFVAL { 1 }
    ::= { saBattery 9 }
    
saBatteryLedPower OBJECT-TYPE
    SYNTAX INTEGER {
        true(0),
        false(1)
    }
    MAX-ACCESS  read-write
    STATUS      current
    DESCRIPTION
        "LED flash mode.
         0: Always keep LEDs in normal power mode.
         1: operate LEDs in low power mode when operating from battery power.
         Note:  See PRD for LED low power modes."
    DEFVAL { 1 }
    ::= { saBattery 10 }


saBatteryRecoverableCapacityA OBJECT-TYPE
    SYNTAX  INTEGER
    UNITS        "mAH"
    MAX-ACCESS 	  read-only
    STATUS        current
    DESCRIPTION	
        "The estimated capacity, in milliampere-hours (mAH), that the battery is able to hold.  
         This estimate is based on the results of the previous partial discharge capacity test."
    ::= { saBattery 11 }
    
saBatteryRecoverableCapacityB OBJECT-TYPE
    SYNTAX  INTEGER
    UNITS        "mAH"
    MAX-ACCESS 	  read-only
    STATUS        current
    DESCRIPTION	
        "The estimated capacity, in milliampere-hours (mAH), that the battery is able to hold.  
         This estimate is based on the results of the previous partial discharge capacity test."
    ::= { saBattery 12 }

saBatteryLastCapacityTestA OBJECT-TYPE
    SYNTAX  DateAndTime
    MAX-ACCESS 	  read-only
    STATUS        current
    DESCRIPTION	
        "The time that the last Recoverable Capacity Test was performed."
    ::= { saBattery 13 }   

saBatteryLastCapacityTestB OBJECT-TYPE
    SYNTAX  DateAndTime
    MAX-ACCESS 	  read-only
    STATUS        current
    DESCRIPTION	
        "The time that the last Recoverable Capacity Test was performed."
    ::= { saBattery 14 }     
    
saBatteryReplacePercentage OBJECT-TYPE
    SYNTAX  INTEGER (0..100)
    UNITS        "percent"
    MAX-ACCESS 	  read-write
    STATUS        current  
    DESCRIPTION	
        "This MIB defines the percentage capacity at which the Replace Battery telemetry will be activated."
    DEFVAL { 55 }          
    ::= { saBattery 15 }  
    
saBatteryKFactorChargeLevel OBJECT-TYPE
    SYNTAX  INTEGER (60..100)
    UNITS        "percent"
    MAX-ACCESS 	  read-write
    STATUS        current  
    DESCRIPTION	
        "Defines the charge level percent to which the internal batteries will be charged."
    DEFVAL { 85 }          
    ::= { saBattery 16 }

saBatteryCurrentStateA OBJECT-TYPE 
	SYNTAX INTEGER {
        missing(0),
        idle(1),
        charging(2),
        discharging(3)
    }
    MAX-ACCESS 	  read-only
    STATUS        current  
    DESCRIPTION	
        "Displays the current state of the Battery.
         missing - indicates that battery is not present in slot
         idle - Indicates the battery is neither charging nor discharging
         charging - Battery is in charge mode
         discharging - Battery is being used to power the EMTA"
    ::= { saBattery 17 }

saBatteryCurrentStateB OBJECT-TYPE 
	SYNTAX INTEGER {
        missing(0),
        idle(1),
        charging(2),
        discharging(3)
    }
    MAX-ACCESS 	  read-only
    STATUS        current  
    DESCRIPTION	
        "Displays the current state of the Battery.
          missing - indicates that battery is not present in slot
          idle - Indicates the battery is neither charging nor discharging
          charging - Battery is in charge mode
          discharging - Battery is being used to power the EMTA"
    ::= { saBattery 18 }

saBatteryRfAmpPower OBJECT-TYPE
    SYNTAX INTEGER {
        enable(0),
        disable(1)
    }
    MAX-ACCESS  read-write
    STATUS      current
    DESCRIPTION
        "Enable/Disable the upstream RF amplifier operating in battery mode.
         0: Always enable upstream RF amplifier 
         1: Shut off the bias current to the upstream RF amplifier when no packets are being sent
            and the EMTA is operating from battery power.            
         Note:  Mode=1: enable RF Amp only when a packet needs to be sent and unit is operating 
         from battery."
    DEFVAL { 1 }
    ::= { saBattery 19 }
         
         
saBatterySerialNumber OBJECT-TYPE
    SYNTAX      DisplayString
    MAX-ACCESS  read-only
    STATUS      current
    DESCRIPTION
        "Battery Serial Number."
    ::= { saBattery 20 }
    
saBatteryDateCode OBJECT-TYPE
    SYNTAX      DisplayString
    MAX-ACCESS  read-only
    STATUS      current
    DESCRIPTION
        "Battery Pack Date Code(mmddyy)"
    ::= { saBattery 21 }
    
-- ================================
-- MTA BATTERY ENDPOINT STARTS HERE
-- ================================

saMtaBatteryEndPointTable   OBJECT-TYPE
    SYNTAX        SEQUENCE OF SaMtaBatteryEndPointEntry
    MAX-ACCESS    not-accessible
    STATUS        current
    DESCRIPTION
       "This table describes the MTA EndPoint
        battery configuration. "
   ::=  { saBattery 1001 }

saMtaBatteryEndPointEntry  OBJECT-TYPE
    SYNTAX        SaMtaBatteryEndPointEntry
    MAX-ACCESS    not-accessible
    STATUS        current
    DESCRIPTION
        " List of attributes for a single MTA endpoint interface."
    INDEX { ifIndex }
    ::= { saMtaBatteryEndPointTable 1 }

SaMtaBatteryEndPointEntry  ::= SEQUENCE {
    saMtaBatteryEndPntPower         INTEGER,
    saMtaBatteryEndPntRingPower     INTEGER,
    saMtaBatteryEndPntOffHookPower  INTEGER
    }


saMtaBatteryEndPntPower OBJECT-TYPE
    SYNTAX INTEGER {
        enable(0),
        disable-later(1),
        disable-always(2)
    }
    MAX-ACCESS  read-write
    STATUS      current
    DESCRIPTION
        "Line working way while operating in battery power.
         0: Enable telephone line (if otherwise enabled) when EMTA is operating 
            on battery power
         1: Enable telephone line (if otherwise enabled) when EMTA is operating 
            on battery power only if this line is in-use at the time of power loss.  
            Disable line after this phone call is completed.
         2: Disable line when EMTA is operating on battery power.
         Note:  If Line 1 and Line 2 are both disabled then shutdown VBH and VBL.
         Default value for line 1 is enable(0) and for line 2 is disable-later(1)."
    ::= { saMtaBatteryEndPointEntry 1 }         

saMtaBatteryEndPntRingPower OBJECT-TYPE
    SYNTAX INTEGER {
        enable(0),
        enable-reduced(1),
        disable-later(2),
        disable-always(3)
    }
    MAX-ACCESS  read-write
    STATUS      current
    DESCRIPTION
        "Line ring power setting while operating in battery power.
         0: Provide normal voltage ring to telephone line number when EMTA is operating 
            on battery power and line is enabled.
         1: Provide reduced voltage ring signal to telephone line number to save power 
            when EMTA is operating on battery power and line is enabled.
         2: Provide reduced voltage ring signal to telephone line number to save power 
            when EMTA is operating on battery power and disable power to ring signal on line 
            when battery is in 'Low power' status and line is enabled.
         3: Disable ring signal on Line on battery power.
         Note: For 3349 based producs:
               Mode 0: VBH = -62V when no ring, VBH = -83V if either phone line is ringing.
               Mode 1: (on battery) VBH = -62V when no line is ringing, VBH = -62 if either 
               line is ringing. (on AC power) VBH = -62V when no line is ringing, VBH = -83V 
               if either line is ringing.
         Note for 3368 based products:
               Mode 0: VBH = -59V when no ring, VBH = -98V if either phone line is ringing.
               Mode 1: (on battery) VBH = -59V when no line is ringing, VBH = -89 if either 
               line is ringing. (on AC power) VBH = -59V when no line is ringing, VBH = -98V 
               if either line is ringing."
    DEFVAL { 1 }
    ::= { saMtaBatteryEndPointEntry 2 }         

saMtaBatteryEndPntOffHookPower OBJECT-TYPE
    SYNTAX INTEGER {
        normal(0),
        reduced(1)
    }
    MAX-ACCESS  read-write
    STATUS      current
    DESCRIPTION
        "Line offhook power setting while operating in battery power.
         0: Provide normal off-hook voltage to telephone line number when EMTA is 
            operating on battery power and line is enabled.
         1: Provide reduced off-hook voltage to telephone line number to save power 
            when EMTA is operating on battery power and line is enabled.
         Note:  Mode=0: VBL = -25V
                Mode=1: (on battery)VBL = -20V(on AC power)VBL = -25V"
    DEFVAL { 1 }
    ::= { saMtaBatteryEndPointEntry 3 }         


-- ================================
-- saBatteryCapacityMib 
-- Note: The following MIB tree is applicable only to HW DPX2213.
-- All other HW models do not support the MIB tree below.
-- ================================
 
saBatteryCapacityMib OBJECT IDENTIFIER ::= { saBattery 1002 }
 
saBatteryCapacityManualTestA OBJECT-TYPE 
 SYNTAX INTEGER {
        normalOperation(0),
        testActive(1),
        testError(2)
        }
    MAX-ACCESS    read-write
    STATUS        current  
    DESCRIPTION 
        "Initiates a manual internal Battery Test for slot A to determine
         the true battery capacity.  The battery test will first ensure
         that a full charge is present on the battery (charging first if
         necessary).  It will then perform a full discharge of the
         battery in force discharge mode.  At the conclusion of the test,
         the battery will then be re-charged to full charge at which point
         the test will be complete.
         This object will read back as a 1 during the battery test.
         Reading 0 will indicate the test is complete.  Manually running a
         test with this MIB will reset the normal schedule for
         automatically initiating the battery test.
         This object will report an error if unable to perform the battery
         test.  Possible causes include:
         1. no AC present
         2. battery test already started on another battery slot.
         After the test has completed, test results are available in the
         following objects:
         1. saBatteryRecoverableCapacityA
         2. saBatteryReplace
         3. saBatteryMissing
         4. saBatteryLow
         WARNING:  This test will run to completion and will impact an
         EMTA's ability to provide full-rated battery backup during the test.
         This test should only be run for diagnostic purposes and never in
         an environment where battery backed-up EMTA operation is critical.
         This test could take up to 24 hours to complete and update the
         results. 
         WARNING:  Repeatedly forcing the Battery Capacity test will reduce
         the battery lifetime.   The battery test should not be run more than
         once every 30 days."
    DEFVAL { 0 }          
    ::= { saBatteryCapacityMib 1 }
 
 
saBatteryCapacityManualTestB OBJECT-TYPE 
 SYNTAX INTEGER {
        normalOperation(0),
        testActive(1),
        testError(2)
        }
    MAX-ACCESS    read-write
    STATUS        current  
    DESCRIPTION 
        "Initiates a manual internal Battery Test for slot B to determine
         the true battery capacity.  The battery test will first ensure
         that a full charge is present on the battery (charging first if
         necessary).  It will then perform a full discharge of the
         battery in force discharge mode.  At the conclusion of the test,
         the battery will then be re-charged to full charge at which point
         the test will be complete.
         This object will read back as a 1 during the battery test.
         Reading 0 will indicate the test is complete.  Manually running a
         test with this MIB will reset the normal schedule for
         automatically initiating the battery test.
         This object will report an error if unable to perform the battery
         test.  Possible causes include:
         1. no AC present
         2. battery test already started on another battery slot.
         After the test has completed, test results are available in the
         following objects:
         1. saBatteryRecoverableCapacityB
         2. saBatteryReplace
         3. saBatteryMissing
         4. saBatteryLow
         WARNING:  This test will run to completion and will impact an
         EMTA's ability to provide full-rated battery backup during the test.
         This test should only be run for diagnostic purposes and never in
         an environment where battery backed-up EMTA operation is critical.
         This test could take up to 24 hours to complete and update the
         results. 
         WARNING:  Repeatedly forcing the Battery Capacity test will reduce
         the battery lifetime.   The battery test should not be run more than
         once every 30 days."
    DEFVAL { 0 }          
    ::= { saBatteryCapacityMib 2 }
 
saBatteryCapacityTestControl OBJECT-TYPE 
 SYNTAX INTEGER {
        manual(0),
        scheduled(1)
        }
    MAX-ACCESS    read-write
    STATUS        current  
    DESCRIPTION 
        "Configures the operation of the forced discharge battery capacity
         test.
         Not scheduled(0) - The battery capacity test will only run when
         initiated via the saBatteryCapacityManualTest[A|B] object.
         scheduled(1) - The battery capacity test runs at a scheduled
         interval defined in saBatteryCapacityScheduleInterval."
    DEFVAL { 1 }          
    ::= { saBatteryCapacityMib 3 }
 
saBatteryCapacityScheduleInterval OBJECT-TYPE
     SYNTAX INTEGER (30..365)
     UNITS "days"
     MAX-ACCESS read-write
     STATUS current
     DESCRIPTION
         "The interval which to run the scheduled Battery Capacity Test. 
          The number of days specified by this object is added to the
          saBatteryLastCapacityTest[A|B] date to determine if a capacity
          test is required.   If the current date is equal to or exceeds
          saBatteryLastCapacityTest[A|B] + saBatteryCapacityScheduleInterval,
          AND saBatteryCapacityTestControl is set to scheduled, then a
          capacity test will begin immediately."
     DEFVAL { 180 }
     ::= { saBatteryCapacityMib 4 }


-- =================================
-- HW COMPONENT OPERATION ON BATTERY
-- =================================

saBatteryIfOperationTable OBJECT-TYPE
    SYNTAX        SEQUENCE OF SaBatteryIfOperationEntry
    MAX-ACCESS    not-accessible
    STATUS        current
    DESCRIPTION
       "This table describes the interface operation on battery
        configuration."
   ::=  { saBattery 1003 }
 
saBatteryIfOperationEntry  OBJECT-TYPE
    SYNTAX        SaBatteryIfOperationEntry
    MAX-ACCESS    not-accessible
    STATUS        current
    DESCRIPTION
        "Per hardware interface battery support definition."
    INDEX { saBatteryIfOperIndex }
    ::= { saBatteryIfOperationTable 1 }
 
SaBatteryIfOperationEntry  ::= SEQUENCE {
    saBatteryIfOperIndex        INTEGER,
    saBatteryIfOperBatteryMode  INTEGER,
    saBatteryIfOperOnTime       INTEGER
    }
 
saBatteryIfOperIndex OBJECT-TYPE
    SYNTAX INTEGER {
        leds(1),
        ethernet(2),
        usbClientPorts(3),
        wireless(4)
        }
     MAX-ACCESS not-accessible
     STATUS current
     DESCRIPTION
         "Interface definition for the purpose of battery power save modes.
          ethernet(2) includes MoCA and DMS if present."
     ::= { saBatteryIfOperationEntry 1 }
 
saBatteryIfOperBatteryMode OBJECT-TYPE
     SYNTAX INTEGER {
         off(0),
         onAlways(1),
         onTimerOff(2)
         }
     MAX-ACCESS read-write
     STATUS current
     DESCRIPTION
         "Defines if the hardware component is enabled or disabled when
          the unit operates on battery power.  Some interfaces (i.e. LEDs) may
          operate in a mode that requires reduced power when set to disabled.
          If set to off(0) the unit the selected interface will be disabled as
          soon as possible after beginning to run on AC power.
          Some interfaces (i.e. DMS and harddisks) may first be placed 
          in a known safe power down state before power to these interfaces is
          disabled. If set to onTimerOff(2), the interface is enabled only for
          time defined in saBatteryIfOperOnTime."
     DEFVAL { 0 }
     ::= { saBatteryIfOperationEntry 2 }
 
saBatteryIfOperOnTime OBJECT-TYPE
     SYNTAX INTEGER (0..28800)
     UNITS "seconds"
     MAX-ACCESS read-write
     STATUS current
     DESCRIPTION
         "Defines time for which the hardware component will stay
          enabled after the unit begins to run on battery power if the interface is 
          set to on-timer-off mode.  After this time expires the interface will
          be disabled."
     DEFVAL { 0 }
     ::= { saBatteryIfOperationEntry 3 }
  
  END
