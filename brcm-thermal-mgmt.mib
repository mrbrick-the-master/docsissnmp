--****************************************************************************
--
-- Copyright (c) 2006-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-thermal-mgmt.mib
--    Author:   Charles Eyles
--    Creation Date: October 4, 2006
--
--****************************************************************************
--    Description:
--
--      private MIB for runtime (not factory) management of the
--              Thermal Monitor
--
--****************************************************************************
--    Revision History:
--
--****************************************************************************

BRCM-THERMAL-MGMT-MIB DEFINITIONS ::= BEGIN

IMPORTS
    MODULE-IDENTITY,
    OBJECT-TYPE,
    Integer32,
    Unsigned32
        FROM SNMPv2-SMI
    TruthValue
        FROM SNMPv2-TC
    cableDataMgmtMIBObjects
        FROM BRCM-CABLEDATA-MGMT-MIB;

thermalMgmt MODULE-IDENTITY
    LAST-UPDATED "201406030000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to thermal monitor."
    REVISION      "201406030000Z"
    DESCRIPTION
        "Removed unused imports."
    REVISION      "200702050000Z"
    DESCRIPTION
        "Module description was updated. 
         Compilability issues were cleaned up:
         - Illegal character was removed from description of objects 
           thermalPowerOnThreshold and thermalPowerOffThreshold."
    REVISION      "200610040000Z"
    DESCRIPTION
        "Initial version of this MIB module."
    ::= { cableDataMgmtMIBObjects 11 }

thermalMgmtBase OBJECT IDENTIFIER ::= { thermalMgmt 1 }

thermalCurrentTemperature OBJECT-TYPE
    SYNTAX      Integer32
    UNITS       "degrees C"
    MAX-ACCESS  read-only
    STATUS      current
    DESCRIPTION
        "The Current Temperature of the Unit."
    ::= { thermalMgmtBase 1 }

thermalPowerOffThreshold OBJECT-TYPE
    SYNTAX      Integer32 (40..120)
    UNITS       "degrees C"
    MAX-ACCESS  read-write
    STATUS      current
    DESCRIPTION
        "Specifies the Temperature Threshold at which the Thermal Shutdown Controller
         will power down the unit. (40C to 120C). Note PowerOffThreshold must be
         greater than PowerOnThreshold."
    ::= { thermalMgmtBase 2 }

thermalPowerOnThreshold OBJECT-TYPE
    SYNTAX      Integer32 (40..120)
    UNITS       "degrees C"
    MAX-ACCESS  read-write
    STATUS      current
    DESCRIPTION
        "Specifies the Temperature Threshold at which the Thermal Shutdown Controller
         will switch power back on. (40C to 120C). Note PowerOnThreshold must be
         less than PowerOffThreshold."
    ::= { thermalMgmtBase 3 }

thermalPowerOnDelay OBJECT-TYPE
    SYNTAX      Unsigned32 (2..50)
    UNITS       "250 Milliseconds"
    MAX-ACCESS  read-write
    STATUS      current
    DESCRIPTION
        "This delay specifies the time between the Thermal Shutdown Controller detecting  
         that the Power On Threshold has been reached and when it actually switches 
         the unit back on. Its purpose is to allow power on the remainder of the board
         to stabilize. Serial communications are blocked during this delay, so it should 
         be chosen carefully. The delay is specified in multiples of 50 milliseconds
         2 to 50 ( 100ms - 2500ms ). The default is value is 5 yielding a delay
         of 250ms."
    ::= { thermalMgmtBase 4 }

thermalPowerOffDelay OBJECT-TYPE
    SYNTAX      Unsigned32 (5..60)
    UNITS       "Seconds"
    MAX-ACCESS  read-write
    STATUS      current
    DESCRIPTION
        "This delay is used to ensure the remainder of the board is completely powered 
         down prior to the Thermal Shutdown Circuit entering Over Temperature state. 
         Because some power supplies may experience a current trip when input power is 
         suddenly removed, this delay must be long enough to ensure the board will 
         successfully power back up following power removal. The delay is specified in 
         seconds; 5 to 60."
    ::= { thermalMgmtBase 5 }

thermalNotificationDelay OBJECT-TYPE
    SYNTAX      Unsigned32 (5..60)
    UNITS       "Seconds"
    MAX-ACCESS  read-write
    STATUS      current
    DESCRIPTION
        "This delay is used to allow the main processor time to clean up (i.e. preserve 
         state information in non-volatile memory, and/or gracefully shut down a battery 
         subsystem) prior to power being removed. The delay is specified in seconds 5 to 
         60. The default value is 10."
    ::= { thermalMgmtBase 6 }

thermalMonitorInitialized OBJECT-TYPE
    SYNTAX      TruthValue
    MAX-ACCESS  read-only
    STATUS      current
    DESCRIPTION
        "This object returns true if the thermal monitor has been successfully initialized."
    DEFVAL { false }
    ::= { thermalMgmtBase 7 }

END
