--****************************************************************************
--
-- Copyright (c) 2004-2012 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************

-- The DOCS-IFEXT2-MIB as presented in OSSIv2[1].0-N-04.0166-3
-- September 15, 2004
--
-- Authored by Eduardo Cardona with additional input from
-- Andre Lejeune (Terayon), Margo Dolas (Broadcom), Guy Cohen (TI), 
-- Yoav Hebron (Conexant), Greg White (CableLabs), Bruce Currivan (Broadcom), 
-- Mike Grimwood (Terayon), Oren Arad (Terayon), Matt Schmitt (CableLabs), 
-- Alberto Campos (CableLabs)
--

DOCS-IFEXT2-MIB DEFINITIONS ::= BEGIN

IMPORTS
    MODULE-IDENTITY,
    OBJECT-TYPE,
    Unsigned32,
    Gauge32
        FROM SNMPv2-SMI
    TruthValue
        FROM SNMPv2-TC
    OBJECT-GROUP,
    MODULE-COMPLIANCE
        FROM SNMPv2-CONF
    ifIndex
        FROM IF-MIB
    TenthdBmV,
    TenthdB
        FROM DOCS-IF-MIB
    clabProjDocsis
        FROM CLAB-DEF-MIB;

docsIfExt2Mib MODULE-IDENTITY
    LAST-UPDATED "201106231700Z" -- June 23, 2011
    ORGANIZATION "Cable Television Laboratories, Inc"
    CONTACT-INFO
        "
        Postal: Cable Television Laboratories, Inc.
        400 Centennial Parkway
        Louisville, Colorado 80027-1266
        U.S.A.
        Phone: +1 303-661-9100
        Fax: +1 303-661-9199
        E-mail: mibs@cablelabs.com"
    DESCRIPTION
        "This MIB module contains the management objects that enhance
        DOCSIS 2.0 feature set.
        It includes SCDMA capability of limiting the number of codes
        assigned to a CM over the total active codes, referred as
        Maximum Scheduled Codes (MSC)."
    REVISION "201106231700Z"
    DESCRIPTION
        "Revised version includes ECN OSSIv3.0-N-11.0997-1
        and published as I15."
    REVISION "201010081700Z"
    DESCRIPTION
        "Revised version includes ECN OSSIv3.0-N-10.0934-1
        and published as I13."
    REVISION "200406231700Z"
    DESCRIPTION
        "Initial version of this MIB module."
    REVISION "200411101700Z"
    DESCRIPTION
        "Re-rooted to clabProjDocsis.5"
    ::= { clabProjDocsis 5 }

-- ---------------------------------------------------------
-- Textual Conventions
-- ---------------------------------------------------------

-- ---------------------------------------------------------------------
-- Main Groups
-- ---------------------------------------------------------------------

docsIfExt2Notifications OBJECT IDENTIFIER ::= { docsIfExt2Mib 0}
docsIfExt2MibObjects    OBJECT IDENTIFIER ::= { docsIfExt2Mib 1}
docsIfExt2BaseObjects   OBJECT IDENTIFIER ::= { docsIfExt2MibObjects 1 }
docsIfExt2CmObjects     OBJECT IDENTIFIER ::= { docsIfExt2MibObjects 2 }
docsIfExt2CmtsObjects   OBJECT IDENTIFIER ::= { docsIfExt2MibObjects 3 }

-- ---------------------------------------------------------------------
-- Base Group Objects
-- Applicable to both CM and CMTS
-- ---------------------------------------------------------------------

-- ---------------------------------------------------------------------
-- CM Group Objects
-- ---------------------------------------------------------------------

-- ---------------------------------------------------------------------
-- CM Maximum Scheduled Codes
-- docsIfExt2CmMscStatusTable extends docsIfUpstreamChannelTable
-- ---------------------------------------------------------------------

docsIfExt2CmMscStatusTable OBJECT-TYPE
    SYNTAX      SEQUENCE OF DocsIfExt2CmMscStatusEntry
    MAX-ACCESS  not-accessible
    STATUS      current
    DESCRIPTION
        "This table extends the docsIfUpstreamChannelTable to report
        the CM MSC status."
    ::= { docsIfExt2CmObjects 1 }

docsIfExt2CmMscStatusEntry OBJECT-TYPE
    SYNTAX      DocsIfExt2CmMscStatusEntry
    MAX-ACCESS  not-accessible
    STATUS      current
    DESCRIPTION
        "As an extension of docsIfUpstreamChannelTable this table has
        entries for each ifEntry with an ifType of
        docsCableUpstream(129)
        This entry is instantiated by the CM only if the
        CM is currently in SCDMA mode."
    INDEX { ifIndex }
    ::= { docsIfExt2CmMscStatusTable 1 }

DocsIfExt2CmMscStatusEntry ::= SEQUENCE {
        docsIfExt2CmMscStatusState INTEGER,
        docsIfExt2CmMscStatusPowerShortfall TenthdB,
        docsIfExt2CmMscStatusCodeRatio Unsigned32,
        docsIfExt2CmMscStatusMaximumScheduledCodes Unsigned32,
        docsIfExt2CmMscStatusPowerHeadroom TenthdB,
        docsIfExt2CmMscStatusEffectivePower TenthdBmV,
        docsIfExt2CmMscStatusIUC2Control INTEGER
    }

docsIfExt2CmMscStatusState OBJECT-TYPE
    SYNTAX      INTEGER {
        channelEnabled(1),
        channelDisabled(2),
        active(3),
        inactive(4),
        unknown(5)
    }
    MAX-ACCESS  read-only
    STATUS      current
    DESCRIPTION
        "Indicates the current state of the Maximum Scheduled Codes
        feature on the CM.
        
        channelEnabled(1) S-CDMA Maximum Scheduled Codes
                is enabled in the UCD TLV-17.
        
        channelDisabled(2) S-CDMA Maximum Scheduled Codes
                is disabled in the UCD TLV-17 or a UCD has been
                received that does not contain that TLV.
        
        active(3) The CM has received a Ranging Response that
                contains a non-zero TLV-10 or non-zero TLV-11
                and therefore has MSC activated. This state
                overrides the channelEnabled(2) state.
        
        inactive(4) The CM has received a Ranging Response that
                does not contain TLV-10 or TLV-11 or has both
                set to 0.This state overrides the
                channelEnabled(2) state.
        
        unknown(5) CM has not yet received a UCD to determine
                if MSC is enabled or disabled on that channel."
    DEFVAL { unknown }
    ::= { docsIfExt2CmMscStatusEntry 1 }

docsIfExt2CmMscStatusPowerShortfall OBJECT-TYPE
    SYNTAX      TenthdB
    UNITS       "TenthdB"
    MAX-ACCESS  read-only
    STATUS      current
    DESCRIPTION
        "Indicates the Power Shortfall at the CM, in units of
        tenth dB.
        The value is provided by the CM and is sent in the RNG-REQ
        message. It is internally calculated in units of quarter
        dB and is rounded upward for this MIB object to the nearest
        tenth dB. A value of zero indicates that the CM has no power
        shortfall."
    REFERENCE
        "Data-Over-Cable Service Interface Specifications: Radio
        Frequency Interface Specification Section 8.3.5"
    DEFVAL { 0 }
    ::= { docsIfExt2CmMscStatusEntry 2 }

docsIfExt2CmMscStatusCodeRatio OBJECT-TYPE
    SYNTAX      Unsigned32 ( 2 | 8 | 16 | 32)
    MAX-ACCESS  read-only
    STATUS      current
    DESCRIPTION
        "Indicates the maximum ratio of number of active codes to
        Maximum Scheduled Codes that the CM can support, as
        reported in the Ranging Request."
    REFERENCE
        "Data-Over-Cable Service Interface Specifications: Radio
        Frequency Interface Specification Section 8.3.5"
    ::= { docsIfExt2CmMscStatusEntry 3 }

docsIfExt2CmMscStatusMaximumScheduledCodes OBJECT-TYPE
    SYNTAX      Unsigned32 (0 | 4..128)
    MAX-ACCESS  read-only
    STATUS      current
    DESCRIPTION
        "Indicates the Maximum Scheduled Codes in use by the CM.
        The value is provided by the CMTS through a TLV value in
        the RNG-RSP message. Note that not all values from 4..128
        are valid.
        A value of zero when docsIfExt2CmMscStatusSate is active(3)
        indicates there is no maximum scheduled codes value. This
        object should remain at zero when
        docsIfExt2CmMscStatusState is not active(3)."
    REFERENCE
        "Data-Over-Cable Service Interface Specifications: Radio
        Frequency Interface Specification Section 8.3.6"
    DEFVAL { 0 }
    ::= { docsIfExt2CmMscStatusEntry 4 }

docsIfExt2CmMscStatusPowerHeadroom OBJECT-TYPE
    SYNTAX      TenthdB
    UNITS       "TenthdB"
    MAX-ACCESS  read-only
    STATUS      current
    DESCRIPTION
        "Indicates the Maximum Scheduled Codes Power Headroom in
        use by the CM, in units of tenth dB. The value is
        provided by the CMTS in units of quarter dB through
        TLV-11 in the RNG-RSP message and is rounded upward for
        this MIB object to the nearest tenth dB. A value of zero
        indicates the CMTS provided no Power Headroom. This
        object should remain at zero when
        docsIfExt2CmMscStatusState is not active(3)."
    REFERENCE
        "Data-Over-Cable Service Interface Specifications: Radio
        Frequency Interface Specification Section 8.3.6"
    DEFVAL { 0 }
    ::= { docsIfExt2CmMscStatusEntry 5 }

docsIfExt2CmMscStatusEffectivePower OBJECT-TYPE
    SYNTAX      TenthdBmV
    UNITS       "TenthdBmV"
    MAX-ACCESS  read-only
    STATUS      current
    DESCRIPTION
        "Indicates the Effective Transmit Power of the CM. This is
        the power that would result hypothetically if, in a
        spreader-on frame, the CM were to transmit on all active
        codes with 64QAM modulation. This object should be equal
        to docsIfCmStatusTxPower when docsIfExt2CmMscStatusState
        is not active(3)."
    REFERENCE
        "Data-Over-Cable Service Interface Specifications: Radio
        Frequency Interface Specification Section 6.2.18.2.2"
    ::= { docsIfExt2CmMscStatusEntry 6 }

docsIfExt2CmMscStatusIUC2Control OBJECT-TYPE
    SYNTAX      INTEGER {
        noIUC2(1),
        limitedIUC2(2),
        freeIUC2(3)
        }
    MAX-ACCESS  read-write
    STATUS  current
    DESCRIPTION
        "The CM usage of IUC2 when MSC is enabled:
        noIUC2(1): CM usage of IUC2 is prohibited
        limitedIUC2(2): CM is allowed to use IUC2 as long as
        the CM does not exceed MSC
        freeIUC2(3): CM is allowed to use IUC2 without regard
        for MSC."
    REFERENCE
        "Data-Over-Cable Service Interface Specifications: Radio
        Frequency Interface Specification Section 6.2.11.6"
    DEFVAL { noIUC2 }
    ::= { docsIfExt2CmMscStatusEntry 7 }

-- ---------------------------------------------------------------------
-- CM Clear Learned MAC Addresses 
-- This configuration control object clears the learned MAC addresses.
-- ---------------------------------------------------------------------

docsIfExt2CmClearLearnedMacAddresses OBJECT-TYPE 
        SYNTAX      TruthValue
        MAX-ACCESS  read-write
        STATUS      current 
        DESCRIPTION 
           "If set to 'true', the CM clears all entries in the CM
            forwarding database for all learned MAC addresses that
            are not eSAFE or provisioned MAC addresses.  Reading
            this object always returns 'false'."
        DEFVAL { false } 
        ::= { docsIfExt2CmObjects 2 } 
         

-- ---------------------------------------------------------
-- Conformance definitions
-- ---------------------------------------------------------

docsIfExt2Conformance   OBJECT IDENTIFIER   ::= { docsIfExt2Mib 2 }
docsIfExt2Compliances   OBJECT IDENTIFIER   ::= { docsIfExt2Conformance 1 }
docsIfExt2Groups        OBJECT IDENTIFIER   ::= { docsIfExt2Conformance 2 }

docsIfExt2Compliance MODULE-COMPLIANCE
    STATUS  current
    DESCRIPTION
        "The compliance statement for DOCSIS 20 enhanced features."
        
MODULE -- docsIfExt2Mib

-- conditionally mandatory groups

GROUP docsIfExt2CmGroup
    DESCRIPTION
        "Group of objects of ehnanced DOCSIS 2.0 features
        applicable to CMs only."

-- conditionally optional groups

docsIfExt2CmGroup OBJECT-GROUP
    OBJECTS {
            docsIfExt2CmMscStatusState,
            docsIfExt2CmMscStatusPowerShortfall,
            docsIfExt2CmMscStatusCodeRatio,
            docsIfExt2CmMscStatusMaximumScheduledCodes,
            docsIfExt2CmMscStatusPowerHeadroom,
            docsIfExt2CmMscStatusEffectivePower,
            docsIfExt2CmMscStatusIUC2Control,
            docsIfExt2CmClearLearnedMacAddresses
        }
    STATUS current
    DESCRIPTION
        "Group of objects implemented in Cable Modems."
    ::= { docsIfExt2Groups 1 }

END
