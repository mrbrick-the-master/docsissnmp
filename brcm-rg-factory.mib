--**************************************************************************
--
-- Copyright (c) 2003-2010 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--                                                                          
--**************************************************************************
--    Filename: brcm-rg-factory.mib
--    Author:   Kevin O'Neal
--    Creation Date: 30-january-2003
--
--**************************************************************************
--    Description:
--
--		private MIB for residential gateway factory
--		
--**************************************************************************
--    Revision History:
--
--**************************************************************************

BRCM-RG-FACTORY-MIB DEFINITIONS ::= BEGIN

IMPORTS
    MODULE-IDENTITY,
    OBJECT-TYPE,
    IpAddress,
    Integer32
        FROM SNMPv2-SMI
    TruthValue,
    DisplayString
        FROM SNMPv2-TC
    cableDataFactory
        FROM BRCM-CABLEDATA-FACTORY-MIB;
                
residentialGatewayFactory MODULE-IDENTITY
    LAST-UPDATED "201007270000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for management and configuration
         of objects used in manufacturing of residential gateway devices."
    REVISION      "201007270000Z"
    DESCRIPTION
        "Added rgeRouterInitialIpMode object."
    REVISION      "200702050000Z"
    DESCRIPTION
        "Module description was updated."
    REVISION      "200301300000Z"
    DESCRIPTION
            "Initial version of this MIB module."
    ::= { cableDataFactory 7 }

-- rgFactoryBase: miscellaneous control/state objects for factory mode    
rgFactoryBase OBJECT IDENTIFIER ::= { residentialGatewayFactory 1 }
        
rgInitialMode OBJECT-TYPE
    SYNTAX      INTEGER {
                    disabled(1),
                    residentialGateway(2),
                    cableHome10(3),
                    cableHome11(4)
                }
    MAX-ACCESS  read-write
    STATUS      deprecated
    DESCRIPTION
        "Sets the initial manufactured / default operational mode of the device 
         with regard to residential gateway behaviour."
    ::= { rgFactoryBase 1 }
    
rgRipAuthEnabled OBJECT-TYPE
    SYNTAX      TruthValue
    MAX-ACCESS  read-write
    STATUS      current
    DESCRIPTION
        "Enables or disables the RIP MD5 authentication."
    ::= { rgFactoryBase 2 }

rgRipAuthKeyValue OBJECT-TYPE
    SYNTAX      DisplayString (SIZE (0..16))
    MAX-ACCESS  read-write
    STATUS      current
    DESCRIPTION
        "Sets the RIP Auth key value."
    ::= { rgFactoryBase 3 }

rgRipAuthKeyId OBJECT-TYPE
    SYNTAX      Integer32 (0..256)
    MAX-ACCESS  read-write
    STATUS      current
    DESCRIPTION
        "Sets the RIP auth key ID"
    ::= { rgFactoryBase 4 }

rgRipReportingInterval OBJECT-TYPE
    SYNTAX      Integer32 (1..16535)
    UNITS       "seconds"
    MAX-ACCESS  read-write
    STATUS      current
    DESCRIPTION
        "Sets the RIP reporting interval."
    ::= { rgFactoryBase 5 }

rgRipUnicastDestIpAddress OBJECT-TYPE
    SYNTAX      IpAddress
    MAX-ACCESS  read-write
    STATUS      current
    DESCRIPTION
        "Sets the unicast destination IP address that will be used for RIP 
         messaging."
    ::= { rgFactoryBase 6 }

rgRipSubnetMask OBJECT-TYPE
    SYNTAX      IpAddress
    MAX-ACCESS  read-write
    STATUS      current
    DESCRIPTION
        "Sets the RIP subnet mask which is AND'ed with the WAN IP address."
    ::= { rgFactoryBase 7 }

rgeRouterInitialIpMode OBJECT-TYPE
    SYNTAX      INTEGER {
                         disabled(1), 
                         ipv4(2), 
                         ipv6(3), 
                         dual(4), 
                         ipv4RG(5), 
                         overrideDisabled(6), 
                         overrideIPv4(7), 
                         overrideIPv6(8), 
                         overrideDual(9), 
                         overrideIPv4RG(10)
              }
    MAX-ACCESS  read-write
    STATUS      current
    DESCRIPTION
        "Toggles ip provisioning modes for eRouter."
    ::= { rgFactoryBase 8 }

END
