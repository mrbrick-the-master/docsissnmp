CM-CERTCLIENT-MIB DEFINITIONS ::= BEGIN

IMPORTS 
    OBJECT-TYPE,
	MODULE-IDENTITY,
    enterprises
         FROM SNMPv2-SMI
               
    InetAddressType, 
    InetAddress 
         FROM INET-ADDRESS-MIB; 
      
cmCertClient MODULE-IDENTITY
   LAST-UPDATED "200206061630Z"
   ORGANIZATION "Motorola"
   CONTACT-INFO "Jason Krasnow
                 Postal: 6450 Sequence Dr.
                 San Diego, CA 92121
                 Tel: +1 858 404-2577
                 Fax: +1 858 404-3480
                 E-mail: jason@motorola.com"
   DESCRIPTION
      "This module defines proprietary MIB variables to support the
       get certificate protocol of the client." 

   REVISION "200206061630Z"
   DESCRIPTION
      "Added MIB objects to configure cert client parameters"
          
       
::= {enterprises
	 gi(1166)  
	 giproducts(1)
	 cm(19)
     27
    }

cmCertClientObjects OBJECT IDENTIFIER ::= { cmCertClient 1 }
	
cmCertDownloadAdminStatus OBJECT-TYPE
        SYNTAX INTEGER {
            initiateCertUpdate(1),
            updateEnabled(2),
            updateDisabled(3)
        }
        MAX-ACCESS  read-write
        STATUS current
        DESCRIPTION
          "This object is used to trigger the Cert Client to download
           a new certificate from the Certificate Server.  If the 
           current value of this object is updateEnabled(2) and 
           initiateCertUpdate(1) is set, the CM shall initiate the 
           certificate update process.  It is an error if 
           initiateCertUpdate(1) is set and the current value of this 
           object is updateDisabled(3) or initiateCertUpdate(1).  This 
           indicates that the certificate update process is disabled 
           or a certificate update is already in progress.
           Upon completion of the certificate upgrade process, this 
           object shall be set to updateEnabled(2).
           At initial startup, this object reflects the either 
           updateEnabled(2) or updateDisabled(3) depending on the setting 
           in the configuration file."
        ::= { cmCertClientObjects 1 }


 cmCertDownloadOperStatus OBJECT-TYPE
        SYNTAX INTEGER {
            updateNeeded(1),
            inProgress(2),
            complete(3),
            failed(4)
        }
        MAX-ACCESS  read-only
        STATUS      current
        DESCRIPTION
            "updateNeeded(1) indicates that no certificate download procedure
             is in effect and that the certificates need to be updated.  
             inProgress(2) indicates that a get certificate download
             is underway, either as a result of provisioning from the 
             configuration file or from direct management action. Complete(3)
             indicates that the certificate upgrade completed successfully or
             the certficates are of the current correct type. 
             Failed(4) indicates that the certificate download failed."
        REFERENCE
             ""
        ::= { cmCertClientObjects 2 }          
 
 cmCertRelayAgentInetAddressType OBJECT-TYPE 
      SYNTAX      InetAddressType 
      MAX-ACCESS  read-write
      STATUS      current 
      DESCRIPTION 
         "The type of IP address of cmCertRelayAgentInetAddress. "
      DEFVAL{ipv4}           
      ::= { cmCertClientObjects 3 }
             
 cmCertRelayAgentInetAddress OBJECT-TYPE 
      SYNTAX      InetAddress 
      MAX-ACCESS  read-write 
      STATUS      current 
      DESCRIPTION 
         "The private IP address of the Relay Agent." 
      DEFVAL {""}
      ::= { cmCertClientObjects 4 }
      
  cmCertRelayAgentPort OBJECT-TYPE 
      SYNTAX      INTEGER 
      MAX-ACCESS  read-write 
      STATUS      current 
      DESCRIPTION 
         "The port number that the Relay Agent uses to listen for 
          Get Certificate request messages." 
      DEFVAL {900}
      ::= { cmCertClientObjects 5 }
      
 cmCertLoggingControl OBJECT-TYPE
        SYNTAX INTEGER {
            enabled(0),
            disabled(1)
         }
        MAX-ACCESS  read-write
        STATUS      current
        DESCRIPTION
            "Controls the logging of messages associated with upgrading
             a certificate."
        DEFVAL {enabled}
         
        ::= { cmCertClientObjects 6 }          

END
