--**************************************************************************
--                                                                          
--    Copyright 2019 Technicolor, Inc. 
--    All Rights Reserved                                                   
--    No portions of this material may be reproduced in any
--    form without the written permission of:                                                
--        Technicolor Connected Home
--        5030 Sugarloaf Parkway
--        Lawrenceville, GA 30044
--        USA
--                                                 
--**************************************************************************

TCH-RG-MIB DEFINITIONS ::= BEGIN
IMPORTS
        MODULE-IDENTITY,
        OBJECT-TYPE,
        enterprises,
        Counter64,
        Integer32,
        IpAddress,
        Unsigned32,
        Counter32
                FROM SNMPv2-SMI
        ifIndex
                FROM IF-MIB
        TEXTUAL-CONVENTION,
        RowStatus,
        DisplayString,
        MacAddress,
        PhysAddress,
        TruthValue,
        DateAndTime
                FROM SNMPv2-TC
        InetAddressType,
        InetAddress,
                InetAddressIPv6,
        InetPortNumber
                FROM INET-ADDRESS-MIB
        SnmpAdminString
                FROM SNMP-FRAMEWORK-MIB ;

tchRg   MODULE-IDENTITY
        LAST-UPDATED    "2020042100000Z"
        ORGANIZATION    "Technicolor Inc."
        CONTACT-INFO    "http://www.technicolor.com"
        DESCRIPTION
            "Controls the behavior of router/wireless functions.
             Can be part of CM configuration file."

		-- History
	REVISION    	"202004210000Z"
        DESCRIPTION     "Added tchRgEdns0Format to determine how MAC will be encoded in edns0 section"

	REVISION        "202004080000Z"
        DESCRIPTION     "SuperWifi remove the AccountID and add IPAddress and RegStatus "

	REVISION    	"202004090000Z"
        DESCRIPTION     "Added branch tchRgEdns0 to support tchRgEdns0Enable, tchRgEdns0Mode, and tchRgEdns0ApplySettings"

	REVISION    	"202004060000Z"
    	DESCRIPTION     "Updated default values and supported/not supported options for tchRgIperfSpeedTest"

	REVISION    	"202003170000Z"
    	DESCRIPTION     "Updated tchRgIpMgmtWanMode to include private option"

	REVISION    	"202003160000Z"
    	DESCRIPTION     "Changed the default value for tchRgIGMPMaxSessions to 30.  Increased the range from 1 to 50
			 Made additional changes to tchRgDot11SuperWifi to get mib to compile."

	REVISION    	"202003040000Z"
    	DESCRIPTION     "Added  tchRgDot11SuperWifi"

	REVISION    	"202001170000Z"
	DESCRIPTION     "Added  tchRgDot11SromCalibrationChanged"

	REVISION    	"202001140000Z"
	DESCRIPTION     "Added  tchRgDot11BssTostagging"

	REVISION	"201911200000Z"
	DESCRIPTION     "Added tchRgDeviceRemoteSSHWanConnectionAttempts and tchRgDeviceRemoteSSHLanConnectionAttempts"

	REVISION	"201911040000Z"
	DESCRIPTION     "Modification to tchRgFirewallTrafficPassThru.
			 The bits for ipSec, pptp, l2tpAlg, pptpAlg, and ipSecAlg are defaulted to true.  They are now RO"

	REVISION	"201911010000Z"
	DESCRIPTION     "Added tchRgDot11SromCalibration  to validate proper WIFI calibration in deployed units"

	REVISION	"201909270000Z"
	DESCRIPTION     "Added tchRgAcl to control access to webui"

	REVISION	"201909260000Z"
	DESCRIPTION     "Added tchRgTracertMgmtTargetAddressType and changed tchRgTracertMgmtTargetAddress type to InetAddress"

        REVISION        "201909220000Z"
        DESCRIPTION     "Add a new MIB tchRgDot11WiFiRadioStatus under tchRgDot11. THis MIB is to fetch the status value of 5g wifi card"

	REVISION	"201908290000Z"
	DESCRIPTION     "update tchRgWifiHotspotInsertDhcpOptionsMask description : changes the delimeter from semicolon, (;), to '0x00'"

	REVISION	"201908280000Z"
	DESCRIPTION     "update tchRgIpMgmtNatSipAlg with default mib description to false"

	REVISION	"201907290000Z"
	DESCRIPTION     "Add tchRgStatsCpuUtilization and changed tchRgMemory to tchRgStats to make it more generic." 

	REVISION	"201907260000Z"
	DESCRIPTION     "Add tchRgDNSRedirectEnable to redirect to help page when internet is down." 

	REVISION	"201907150000Z"
	DESCRIPTION     "Added OIDs for 3g/4g backup, tchRg3g4g." 

	REVISION	"201907100000Z"
	DESCRIPTION     "Added OIDs for tchRgIGMPMaxSessions, tchRgFirewallPortFwdAddressType, and tchRgDot11AccessMacDeviceName. 
                         Modifications have been made to tchRgFirewallTrafficPassThru to support ALGs."

	REVISION	"201907030000Z"
	DESCRIPTION     "Add mibs to manage dslite precedence of FQDN (dhcp or static)."
	
	REVISION	"201906200000Z"
	DESCRIPTION     "Added new parameter value enabledAndclear(4) in tchRgWifiHotspotProtect MIB."

	REVISION	"201906070000Z"
	DESCRIPTION     "Added tchRgWifiHotspotProtect to allow enable/disable of automated ACL filling feature via MIB."
	
	REVISION	"201905300000Z"
	DESCRIPTION     "Extended tchRgWifiHotspotInsertDhcpOptionsMask to support options 0x100 and 0x200.
			 Added tchRgL2ogreSecRemoteResolvedAddress, tchRgL2ogreSecRemoteAddressResolvedType, tchRgL2ogrePriRemoteResolvedAddress, 
			 and tchRgL2ogrePriRemoteAddressResolvedType to support the resolution of a remote endpoint when an FQDN is entered.
			 Added tchRgAppsLnxUsbMountTable to support USB auto mount feature."

	REVISION	"201905160000Z"
	DESCRIPTION     "Added tchRgTracertMgmt to allow control of traceroute feature via MIB."
	
	REVISION	"201905060000Z"
	DESCRIPTION     "Added tchRgIpMgmtEdns0Enable to control the eDNS0 activation state. Default behavior is disabled (0)."

	REVISION	"201905010000Z"
	DESCRIPTION     "Added tchRgDot11BssPMFcontrol to control use of PMF, Protected Management Frames"

	REVISION	"201903200000Z"
	DESCRIPTION     "Added tchRgDot11ACSExcludeTable, for ACS exclude channels, and modified tchRgFirewallIpv6
                         to control all IPv6 firewall levels"

	REVISION	"201902260000Z"
	DESCRIPTION     "Fix typo in tchRgEventLogTypeIndex."

	REVISION        "201902220000Z"
        DESCRIPTION     "Added new mib tchRgDot11ExtWpsAPPinEnable."
		
        REVISION        "201901040000Z"
        DESCRIPTION     "Added mib group tchRgIpMgmtLanAddrIpv6Dhcp and new parameter tchRgIpMgmtLanAddrIpv6DhcpLeaseTime."

	REVISION        "201901020000Z"
	DESCRIPTION     "Added OID tchRgFirewallPortFwdStatus. Return 1 if at least one port forwarding rule is configured 0 otherwise
                   Add missing previous OID  : tchRgFirewalIPortScanDetection tchRgFirewallIPFloodDetection"

	REVISION        "201812180000Z"
	DESCRIPTION     "Added OID tchRgRapidCommitEnable. DHCPv6 exchange will only use 2 messages instead of 4
                         Fix typo in tchRgDeviceRemoteSSHAccess OID mapping and many compilation issues."

	REVISION        "201812070000Z"
        DESCRIPTION     "Added OID tchRgIGMPEnable and tchRgIperfSpeedTest."

	REVISION        "201812060000Z"
        DESCRIPTION     "Added OID tchRgDot11ClientCounterTable, tchRgDot11ClientCounter. Show number of connected clients for each SSID"

        REVISION        "201811290000Z"
        DESCRIPTION     "Added mib group tchRgDot11AccessMacAnonymousTable group. 
                         Used to display the Mac Access Control List in an anonymous way.
                         VFG Requirement"

	REVISION        "201811270000Z"
        DESCRIPTION     "Added mib group tchRgEvent for consulting and configuring events logs for eRouter and WiFi.
                         Tables with two indexes allow the model to be extensible by adding more log types.
			 Syslog server configuration for those events is not supported yet."

	REVISION        "201811120000Z"
        DESCRIPTION     "Added mib group tchRgMemory group. The group, tchRgMemory, is used to display the RAM statistics of the gateway"

	REVISION        "201811010000Z"
        DESCRIPTION     "Added mib group tchRgDNSTable. The table, tchRgDNSTable, is used to setup DynDNS parameters 
                         Added OID tchRgDNSLanGuiURL. The OID, tchRgDNSLanGuiURL, is used to DNS name for WebGUI from LAN. 
                         Added OID tchRgIPv6PDSize. The OID, tchRgIPv6PDSize, is used to request Size from client to CMTS. "

	REVISION        "201809280000Z"
        DESCRIPTION     "Added mib group tchRgDeviceRemoteSSHAccess for control and config of SSH server."

	REVISION        "201809070000Z"
        DESCRIPTION     "Added mib tchRgdot11nExtUNII2ExtChannelEnable enable/disable UNII2 ext channels"

	REVISION        "201808160000Z"
        DESCRIPTION     "Added more interfaces to tchRgPingMgmtInterface. Added tchRgDNSLanGuiURL"

	REVISION        "201807060000Z"
        DESCRIPTION     "Added new MIB: tchRgDot11ExtPowerSaveSupport, tchRgIpMgmtDhcpFixedIpRemove, tchRgFirewallPortFwdRemove. New option added to tchRgDot11BssPrimarySsidType"
		
        REVISION        "201804270000Z"
        DESCRIPTION     "Added new MIB tchRgFirewallSecurityDoS. Change name of tchRgdot11nExtIgnoreHotspotStatus to tchRgdot11nExtKeepRadioAlive"

	REVISION 	"201710250000Z"
	DESCRIPTION     "Adding new MIB : tchRgIGMPVersion, tchRgdot11nExtBSenable, tchRgIGMPTransferFeature and tchRgAppsLnxUsbEnable. 
					 Adding value to tchRgL2ogreOrigIf"

        REVISION        "201609130000Z"
        DESCRIPTION     "Initial module release."

        ::= { tchModules 2 }

technicolor             OBJECT IDENTIFIER ::= { enterprises 46366 }
tchCableBroadband       OBJECT IDENTIFIER ::= { technicolor 4292 }
tchModules    OBJECT IDENTIFIER ::= { tchCableBroadband 79 }

        
TchRgWebWizardSetup ::= TEXTUAL-CONVENTION
    STATUS       obsolete
    DESCRIPTION
         "WebWizard Setup sections."
    SYNTAX BITS {
        basicPasswordSettings(0),
        basicSetTime(1),
        basicNetworkConfiguration(2),
        basicLAN(3),
        basicFixedCPE(4),
        basicRestart(5),
        basicSaveConfigurationPC(6),
        advancedOptions(7),
        advancedIPFiltering(8),
        advancedMACFiltering(9),
        advancedPortFiltering(10),
        advancedPortForwarding(11),
        advancedPortTriggers(12),
        advancedDMZ(13),
        advancedPassThrough(14),
        advancedNetworkingFeatures(15),
        advancedVPN(16),
        advancedSaveConfigurationServer(17),
        firewallOptions(18),
        firewallEvent(19),
        parentalUserSetup(20),
        parentalBasicRules(21),
        parentalTODRules(22),
        parentalLocalLog(23),
        wirelessBasic(24),
        wirelessSecurity(25),
        wirelessAdvanced(26),
        wirelessAccessControl(27),
        wirelessBridging(28),
        wirelessMultimedia(29),
        basicDDNS(30),
        remoteAccess(31)
        }

TchRgWebWizardSetup2 ::= TEXTUAL-CONVENTION
    STATUS       obsolete
    DESCRIPTION
         "WebWizard Setup sections."
    SYNTAX BITS {
        bridgeRouterMode(0),
        docsisSignal(1),
        docsisStatus(2),
        docsisLog(3),
        --timeUseNtp(4),
        timeZone(5),
        timeDst(6),
        --timeServer(7),
        lanIp(8),
        lanDhcpEnable(9),
        lanDhcpScope(10),
        lanDhcpLeaseTime(11),
        lanDhcpDns(12),
        --lanDhcpWins(13),
        lanFixedCpe(14),
        wanStaticIp(15),
        wanDns(16),
        wanMtu(17),
        --wanHostDomainNames(18),
        --resetModem(19),
        resetFactoryDefaults(20),
        backupConfigToPc(21),
        ddns(22),
        wanBlocking(23),
        ipsecPassthrough(24),
        pptpPassthrough(25),
        remoteManagement(26),
        --multicastPassthrough(27),
        upnpEnable(28),
        ipFiltering(29),
        macFiltering(30),
        portFiltering(31),
        portForwarding(32),
        portTriggers(33),
        dmz(34),
        vpnTermination(35),
        --staticRoute(36),
        firewallFilterProxy(37),
        firewallFilterCookies(38),
        firewallFilterJavaApplets(39),
        firewallFilterActiveX(40),
        firewallFilterPopupWindows(41),
        firewallBlockFragmentedPackets(42),
        portScanDetection(43),
        ipFloodDetection(44),
        firewallProtection(45),
        --firewallEventLogging(46),
        parentalControl(47),
        wireless2p4Enable(48),
        wireless2p4ABGNMode(49),
        wireless2p4SSID(50),
        wireless2p4BroadcastSSID(51),
        wireless2p4Channel(52),
        wireless2p4ChannelWidth(53),
        wireless2p4Security(54),
        wireless2p4Wps(55),
        wireless2p4Advanced(56),
        wireless2p4AccessControl(57),
        wireless2p4Bridging(58),
        wireless2p4Wmm(59),
        wireless2p4AckEnable(60),
        wireless5Enable(61),
        wireless5ABGNMode(62),
        wireless5SSID(63),
        wireless5BroadcastSSID(64),
        wireless5Channel(65),
        wireless5ChannelWidth(66),
        wireless5Security(67),
        wireless5Wps(68),
        wireless5Advanced(69),
        wireless5AccessControl(70),
        wireless5Bridging(71),
        wireless5Wmm(72),
        wireless5AckEnable(73),
        ping(74),
        igmpProxy(75),
        usbSetting(76),
        nas(77),
        mediaServer(78)
        }

TchRgTimeZone ::= TEXTUAL-CONVENTION
    STATUS       current
    DESCRIPTION
         "Time zones."
    SYNTAX INTEGER {
        gmtMinusTwelveEniwetokKwajalein(1),
        gmtMinusElevenMidwayIslandSamoa(2),
        gmtMinusTenHawaii(3),
        gmtMinusNineAlaska(4),
        gmtMinusEightPacificTimeCanadaTijuana(5),
        gmtMinusSevenArizona(6),
        gmtMinusSevenMountainTimeCanada(7),
        gmtMinusSixCentralAmerica(8),
        gmtMinusSixCentralTimeCanada(9),
        gmtMinusSixMexicoCity(10),
        gmtMinusSixSaskatchewan(11),
        gmtMinusFiveBogotaLimaQuito(12),
        gmtMinusFiveEasternTimeCanada(13),
        gmtMinusFiveIndianaEast(14),
        gmtMinusFourAtlanticTimeCanada(15),
        gmtMinusFourCaracasLaPaz(16),
        gmtMinusFourSantiago(17),
        gmtMinusThreeThirtyNewfoundland(18),
        gmtMinusThreeBrasilia(19),
        gmtMinusThreeBuenosAiresGeorgetown(20),
        gmtMinusThreeGreenland(21),
        gmtMinusTwoMid-Atlantic(22),
        gmtMinusOneAzores(23),
        gmtMinusOneCapeVerdeIs(24),
        gmtZeroCasablancaMonrovia(25),
        gmtZeroDublinEdinburghLisbonLondon(26),
        gmtPlusOneAmsterdamBerlinRomeStockholmVienna(27),
        gmtPlusOneBelgradeBratislavaBudapestLjubljanaPrague(28),
        gmtPlusOneBrusselsCopenhagenMadridParis(29),
        gmtPlusOneSarajevoSkopjeSofijaVilniusWarsawZagreb(30),
        gmtPlusOneWestCentralAfrica(31),
        gmtPlusTwoAthensIstanbilMinsk(32),
        gmtPlusTwoBucharest(33),
        gmtPlusTwoHelsinkiRigaTallinn(34),
        gmtPlusTwoJerusalem(35),
        gmtPlusThreeBaghdad(36),
        gmtPlusThreeMoscowStPetersburgVolgograd(37),
        gmtPlusThreeNairobi(38),
        gmtPlusThreeThirtyTehran(39),
        gmtPlusFourAbuDhabiMuscat(40),
        gmtPlusFourThirtyKabul(41),
        gmtPlusFiveEkaterinburg(42),
        gmtPlusFiveThirtyCalcuttaChennaiMumbaiNewDelhi(43),
        gmtPlusFiveFourtyFiveKathmandu(44),
        gmtPlusSixAlmatyNovosibirsk(45),
        gmtPlusSixAstanaDhaka(46),
        gmtPlusSixThirtyRangoon(47),
        gmtPlusSevenBangkokHanoiJakarta(48),
        gmtPlusSevenKrasnoyarsk(49),
        gmtPlusEightBeijingChongqingHongKongUrumqi(50),
        gmtPlusEightIrkustkUlaanBataar(51),
        gmtPlusEightKualaLumpurSingapore(52),
        gmtPlusEightTaipei(53),
        gmtPlusNineOsakaSapporoTokyo(54),
        gmtPlusNineSeoul(55),
        gmtPlusNineThirtyAdelaide(56),
        gmtPlusTenBrisbane(57),
        gmtPlusTenVladivostok(58),
        gmtPlusElevenMagadanSolomonIsNewCaledonia(59),
        gmtPlusTwelveAucklandWellington(60),
        gmtPlusTwelveFiji(61),
        gmtPlusThirteenNukuAlofa(62)
        }

-- RG Device

tchRgDevice   OBJECT IDENTIFIER ::=  { tchRg 1 }

tchRgDeviceBase   OBJECT IDENTIFIER ::=  { tchRgDevice 1 }

tchRgDeviceMode OBJECT-TYPE
    SYNTAX INTEGER { 
        disable(0),
        multiSsid(1),
        cableHome11(2),
                ipv4(3),
                ipv6(4),
                dualstack(5) }
    MAX-ACCESS    read-write
    STATUS        current
    DESCRIPTION
        "Defines the mode of operation for the device.
        This parameter is stored in non-vol and is multiSsid(1) by default.
        Setting this object via SNMP will cause
        the unit to reboot.
                This MIB will be superseded in the config file by TLV202.
                This MIB will read the proper value if set from TLV202.
                This MIB will be superseded by tchRgIpMgmtLanMode inbridge(1) or mixed(4).
                disable(0):  Value will reflect when TLV202 is set to 0. Not all platforms have this value implemented.
                multiSsid(1): Default Value. Value supports IPv4RG with multiple SSID
                        configuration and bridge mode via tchRgIpMgmtLanMode MIB.
                        Bridge mode is the same as eRouter disabled mode.
                        IPV4RG is the non eRouter behavior that existed before
                        in our router products.
                cableHome11(2): <deprecated>. Mode is not supported for eRouter devices.
                Ipv4(3): eRouter IPv4 only mode
                Ipv6(4): eRouter IPv6 only mode
                Dualstack(5): eRouter IPv4 and IPv6 dualstack
                Note: cableHome11(2) is deprecated."
    DEFVAL { 1 }
    ::= { tchRgDeviceBase 1 }


tchRgDeviceResetDefaultEnable OBJECT-TYPE
    SYNTAX TruthValue
    MAX-ACCESS read-write
    STATUS current
    DESCRIPTION
        "This object controls the reset to factory default functionality
         of the gateway. This prevents the local user from using the reset
         switch to gain access to the setup pages using the default user
         name and password. The objective is to prevent theft of service
         from a user who reconfigures the device to add users or change
         wireless settings.
         Enable (object set to true):
          1. Momentary press of the Reset Switch (<5 seconds)
             DOCSIS restart of the modem (reboot, no reset to factory
             default values).
          2. Pressing the reset switch for >5 seconds
             Reboots and resets of all values (modem and router) to
             factory default.
         Disable (object set to false):
          1. Momentary press of the Reset Switch (<5 seconds)
             DOCSIS restart of the modem (reboot, no reset to factory
             default values).
          2. Pressing the reset switch for >5 seconds
             Modem reboots and resets only the cable modem settings to
             factory default values. The router settings should remain and
             should not NOT reset to factory default."
    DEFVAL { true }
    ::= { tchRgDeviceBase 2 }

tchRgDeviceRemoteWebAccessEnable OBJECT-TYPE
    SYNTAX      TruthValue
    MAX-ACCESS  read-write
    STATUS      current
    DESCRIPTION
            "Controls web page access to the WAN IP address on the gateway.
             If DMS is available in the hardware, and tchRgDmsBaseWebRedirect
             is set to true, enabling this feature means to enable port
             forwarding for web access to the DMS (to port 80). Note: the
             entry for this does not appear in port forwarding table or on
             the web pages. Example of the rule: WAN_IP:8080->DMS_IP:80.
             This value is stored in non-vol and is false after factory reset.
             This value can be controlled via a setup web page.

             NOTE: This MIB is applicable only for legacy style web pages"
    ::= { tchRgDeviceBase 3 }

tchRgDeviceRemoteWebAccessPort OBJECT-TYPE
    SYNTAX      InetPortNumber
    MAX-ACCESS  read-write
    STATUS      current
    DESCRIPTION
            "Defines what port to use for the WAN IP address of the gateway
             to be able to access RG web pages.
             This value is to be stored in non-vol and will persist across reboots.
             Only a factory reset would clear it"
    DEFVAL { 8080 }
    ::= { tchRgDeviceBase 4 }

tchRgDeviceAdminReadOnly OBJECT-TYPE
    SYNTAX INTEGER {
        none(0),
        wan(1)
        }
    MAX-ACCESS    read-write
    STATUS        obsolete
    DESCRIPTION
        "This object can restrict admin right of access to the RG web pages.
         If set to wan(1), admin will be restricted to read-write access
         from the WAN interface."
    DEFVAL { 0 }
    ::= { tchRgDeviceBase 5 }

tchRgDeviceLanLanIsolation OBJECT-TYPE
    SYNTAX INTEGER {
        disable(0),
        enable(1)
        }
    MAX-ACCESS    read-write
    STATUS        current
    DESCRIPTION
        "This MIB is only available in D3.0 products.
          This MIB does not take effect if the modem is in VLAN mode i.e if tchRgIpMgmtLanMode.32=vlan(5).
        Lan-Lan Isolation allows you block IP access between CPEs connected to the Ethernet ports.
        Use this mib in conjunction with tchRgDeviceLanWlanIsolation and tchRgDot11BssApIsolation.x for
          complete isolation between CPEs connected to the RG.
        This MIB is written to non-vol and set to disable(0) after a factory reset.
        disable(0)- No Isolation
        enable(1)- Enable Isolation feature"
    DEFVAL { 0 }
    ::= { tchRgDeviceBase 6 }

tchRgDeviceLanWlanIsolation OBJECT-TYPE
    SYNTAX INTEGER {
        disable(0),
        enable(1)
        }
    MAX-ACCESS    read-write
    STATUS        current
    DESCRIPTION
        "This MIB is only available in D3.0 products.
        This MIB does not take effect if the modem is in VLAN mode i.e if tchRgIpMgmtLanMode.32=vlan(5).
        Lan-Wlan Isolation allows you block IP access between CPEs connected to the Ethernet port and
        Wireless SSIDs.
        Use this mib in conjunction with tchRgDeviceLanLanIsolation and tchRgDot11BssApIsolation.x for
          complete isolation between CPEs connected to the RG.
        This MIB is written to non-vol and set to disable(0) after a factory reset.
        disable(0)- No Isolation
        enable(1)- Enable Isolation feature"
    DEFVAL { 0 }
    ::= { tchRgDeviceBase 7 }

tchRgDeviceIpv6Trans OBJECT-TYPE
    SYNTAX INTEGER {
        disable(0),
        dslite(1)
        }
    MAX-ACCESS    read-only
    STATUS        current
    DESCRIPTION
        "This MIB will control which IPv6 transition technology is enabled on the device.
        After setting this MIB to disable in the config file, IPv4 traffic will pass normally
                through the device. When switched to dslite, the DSLite feature will be enabled.
                If eRouter is in IPv6-only mode, DS Lite will tunnel IPv4 traffic over IPv6 to the AFTR
                address specified either manually or in the DHCPv6 option-64. See tchRgDslite MIB tree
                for more details.
        If this setting is changed by the config file, the CM will reboot.
        This MIB is written to non-vol and set to disable(0) after a factory reset.
        disable(0) - No technology is enabled
        enable(1) - DS lite feature is enabled"
    DEFVAL { 0 }
    ::= { tchRgDeviceBase 8 }

tchRgDeviceIpv6Passthrough OBJECT-TYPE
     SYNTAX INTEGER {
        disable(0),
        enable(1)
        }
    MAX-ACCESS    read-write
    STATUS        current
    DESCRIPTION
        "This MIB controls IPv6 passthrough on the RG and is applicable in bridge and router modes.

          When disabled the RG will function without any IPv6 passthrough

          When IPv6 passthrough is enabled in Bridge Mode the RG will drop all IPv4 traffic

          When IPv6 passthrough is enabled in router mode the RG will operate as normal for IPv4 traffic, but all IPv6 traffic will passthrough

          This MIB requires CM reboot.

          This MIB is written to non-vol and set to disable(0) after a factory reset."

    DEFVAL { 0 }
    ::= { tchRgDeviceBase 9 }


tchRgDeviceRemoteSSHAccess   OBJECT IDENTIFIER ::=  { tchRgDeviceBase 10 }

tchRgDeviceRemoteSSHAccessEnable OBJECT-TYPE
    SYNTAX TruthValue
    MAX-ACCESS read-write
    STATUS current
    DESCRIPTION
        "This object controls the SSH service on RG side. It allows to enable
	 the service, which shall be disabled by default. Other mandatory parameters
	 must have been previously set (User, Password, ...).
	 This mechanism assumes that the interface and port to use are already known and 
	 routing/forwarding are setup (possibly implemented on CM side).
	 A default idle timeout of 10 minutes applies, leading to disabling completely 
	 the service.  
         Enable (object set to true):
	     SSH server is started.
         Disable (object set to false):
	     SSH server is disabled (not running at all)."
    DEFVAL { false }
    ::= { tchRgDeviceRemoteSSHAccess 1 }

tchRgDeviceRemoteSSHAccessUser OBJECT-TYPE
    SYNTAX      SnmpAdminString (SIZE (0..64))
    MAX-ACCESS  read-write
    STATUS      current
    DESCRIPTION
        "The user name to use to authenticate on SSH server.
	 Note that no default value exists."
    ::= { tchRgDeviceRemoteSSHAccess 2 }

tchRgDeviceRemoteSSHAccessPassword OBJECT-TYPE
    SYNTAX      SnmpAdminString (SIZE (6..64))
    MAX-ACCESS  read-write
    STATUS      current
    DESCRIPTION
        "The password to use to authenticate on SSH server.
	 Note that no default value exists."
    ::= { tchRgDeviceRemoteSSHAccess 3 }

tchRgDeviceRemoteSSHAccessTimeFrame OBJECT-TYPE
    SYNTAX Unsigned32
    MAX-ACCESS  read-write
    STATUS      current
    DESCRIPTION
        "This parameter is the timeframe (in s) to start the session once
	 the service has been enabled. After this duration, without connection,
	 the service is disabled. Only started connections can remain alive."
	 DEFVAL { 600 }
    ::= { tchRgDeviceRemoteSSHAccess 4 }

tchRgDeviceRemoteSSHRgWanConnectionAttempts OBJECT-TYPE
    SYNTAX      INTEGER
    MAX-ACCESS  read-write
    STATUS      current
    DESCRIPTION
        "Number of Attempts to Connect to SSH via Wan, successful or not"
    ::= { tchRgDeviceRemoteSSHAccess 5}

tchRgDeviceRemoteSSHCmWanConnectionAttempts OBJECT-TYPE
    SYNTAX      INTEGER
    MAX-ACCESS  read-write
    STATUS      current
    DESCRIPTION
        "Number of Attempts to Connect to SSH via Wan, successful or not"
    ::= { tchRgDeviceRemoteSSHAccess 6}

tchRgDeviceRemoteSSHWanConnectionIpType OBJECT-TYPE
    SYNTAX InetAddressType
    MAX-ACCESS  read-write
    STATUS      current
    DESCRIPTION
        "Type of IP, IPv4 of IPv6, of WAN Address attempting to connect to SSH.
         The below are the values for InetAddressType
	 unknown (0), An unknown address type.
	 ipv4(1), An IPv4 address as defined by the InetAddressIPv4 textual convention.
	 ipv6(2), An IPv6 address as defined by the InetAddressIPv4 textual convention."
    ::= { tchRgDeviceRemoteSSHAccess 7}

tchRgDeviceRemoteSSHWanConnectionIp OBJECT-TYPE
    SYNTAX      InetAddress
    MAX-ACCESS  read-write
    STATUS      current
    DESCRIPTION
        "IP of WAN attempting to connect to SSH"
    ::= { tchRgDeviceRemoteSSHAccess 8}

tchRgDeviceRemoteSSHRgLanConnectionAttempts OBJECT-TYPE
    SYNTAX      INTEGER
    MAX-ACCESS  read-write
    STATUS      current
    DESCRIPTION
        "Number of Attempts to Connect to SSH via Lan, successful or not"
    ::= { tchRgDeviceRemoteSSHAccess 9}

tchRgDeviceRemoteSSHCmLanConnectionAttempts OBJECT-TYPE
    SYNTAX      INTEGER
    MAX-ACCESS  read-write
    STATUS      current
    DESCRIPTION
        "Number of Attempts to Connect to SSH via Lan, successful or not"
    ::= { tchRgDeviceRemoteSSHAccess 10}

tchRgDeviceRemoteSSHLanConnectionIpType OBJECT-TYPE
    SYNTAX InetAddressType
    MAX-ACCESS  read-write
    STATUS      current
    DESCRIPTION
        "Type of IP, IPv4 of IPv6, of LAN Address attempting to connect to SSH
         The below are the values for InetAddressType
	 unknown (0), An unknown address type.
	 ipv4(1), An IPv4 address as defined by the InetAddressIPv4 textual convention.
	 ipv6(2), An IPv6 address as defined by the InetAddressIPv4 textual convention."
    ::= { tchRgDeviceRemoteSSHAccess 11}

tchRgDeviceRemoteSSHLanConnectionIp OBJECT-TYPE
    SYNTAX      InetAddress
    MAX-ACCESS  read-write
    STATUS      current
    DESCRIPTION
        "IP of LAN attempting to connect to SSH"
    ::= { tchRgDeviceRemoteSSHAccess 12}

tchRgDeviceFactoryReset  OBJECT-TYPE
    SYNTAX INTEGER {
                false(0),
        routerAndWifi(1),
        routerOnly(2),
        wifi(3)
        }
        MAX-ACCESS      read-write
        STATUS          current
        DESCRIPTION
        "Set routerAndWifi(1) to restore default settings of both the router and wifi.
                Set routerOnly(2) to restore default settings of the router.
                Set wifi(3) to restore default settings of the wifi.
                Return false(0) when read."
        DEFVAL { 0 }
        ::= { tchRgDeviceBase 1002 }

tchRgDeviceReset OBJECT-TYPE
    SYNTAX INTEGER {
                false(0),
        routerAndWifi(1),
        routerOnly(2),
        wifi(3)
        }
    MAX-ACCESS  read-write
    STATUS      current
    DESCRIPTION
                "Set routerAndWifi(1) to reboot the router and WiFi.
                Set routerOnly(2) to reboot the router.
                Set wifi(3) to reboot the WiFi.
                Return false(0) when read."
        DEFVAL { 0 }
        ::= { tchRgDeviceBase 1003 }

tchRgDeviceConfigBackup   OBJECT IDENTIFIER ::=  { tchRgDevice 2 }

tchRgDevConfBackupServerType OBJECT-TYPE
    SYNTAX InetAddressType
    MAX-ACCESS read-write
    STATUS current
    DESCRIPTION
        ""
    DEFVAL { ipv4 }
    ::= { tchRgDeviceConfigBackup 1 }

tchRgDevConfBackupServer OBJECT-TYPE
    SYNTAX  InetAddress
    MAX-ACCESS  read-write
    STATUS current
    DESCRIPTION
        "The address of the TFTP server used for RG config download or upload.
         If the TFTP server is unknown, return 0.0.0.0."
    ::= { tchRgDeviceConfigBackup 2 }


tchRgDevConfBackupFilename OBJECT-TYPE
    SYNTAX      SnmpAdminString (SIZE (0..64))
    MAX-ACCESS  read-write
    STATUS      current
    DESCRIPTION
        "The file name of the config file to be download or upload.
         If unknown, the string '(unknown)' is returned."
    ::= { tchRgDeviceConfigBackup 3 }


tchRgDevConfBackupOperStatus OBJECT-TYPE
    SYNTAX INTEGER {
        inProgress(1),
        complete(2),
        failed(3),
        other(4)
        }
    MAX-ACCESS  read-only
    STATUS      current
    DESCRIPTION
        "InProgress(1) indicates that a TFTP download or upload is underway,
         Complete(2) indicates that the last download or upload is successful,
         failed(3) indicates that the last attempted download or upload is falied."
    ::= { tchRgDeviceConfigBackup 4 }


tchRgDevConfBackupAdminStatus OBJECT-TYPE
    SYNTAX INTEGER {
        download(1),
        upload(2)
        }
    MAX-ACCESS  read-write
    STATUS      current
    DESCRIPTION
        "If set to download(1), the device will initiate a
         TFTP RG config file download using remoteProvisionFilename.
         If set to upload(2), the device will initiate a TFTP RG config file
         upload to remoteProvisionServer. The filename will be the same as
         remoteProvisionFilename.
         At initial startup, this object has the default value of
         download(1)."
    ::= { tchRgDeviceConfigBackup 5 }


tchRgDeviceUserAccess OBJECT IDENTIFIER ::= { tchRgDevice 3 }

tchRgDevUserLanAccessEnabled OBJECT-TYPE
    SYNTAX TruthValue
    MAX-ACCESS read-write
    STATUS obsolete
    DESCRIPTION
        "Defines whether user level access is allowed to the SET-UP web pages
         from the LAN side.
         This MIB is only available in D20.
         This parameter is stored in non-vol and is true after factory
         reset."
    ::= { tchRgDeviceUserAccess 1 }

tchRgDevUserAccessDefaultPassword OBJECT-TYPE
    SYNTAX SnmpAdminString
    MAX-ACCESS read-write
    STATUS obsolete
    DESCRIPTION
        "Defines default password for user.
         If user's password matches the default password (meaning user has
         not changed the password), a change password page comes out every
         time a user connects to the web pages.
         If user's password does not match the default password (meaning user
         has changed it) the change password page does not show.
         This parameter is stored in non-vol and is blank by default.
         If the default password is blank in non-vol (after factory
         default for example), it gets populated with this object's value."
    ::= { tchRgDeviceUserAccess 2 }

tchRgDevUserAccessClearPassword OBJECT-TYPE
    SYNTAX TruthValue
    MAX-ACCESS read-write
    STATUS obsolete
    DESCRIPTION
        "Clears user passwords if set to true (clear=set to default).
         Always returns false when read."
    DEFVAL { false }
    ::= { tchRgDeviceUserAccess 3 }

tchRgDeviceUserAccessReadPages OBJECT-TYPE
    SYNTAX TchRgWebWizardSetup
    MAX-ACCESS read-only
    STATUS obsolete
    DESCRIPTION
        "Specifies the read access rights for every section of the WebWizard-Setup.
         The value of (1) means read-only, the value of (0) means no-access.
         If a write access to a web page is enabled, read access is also enabled.
         The value of this objects is stored in non-vol.
         Default value after factory reset is 0xffffffff."
    ::= { tchRgDeviceUserAccess 4 }

tchRgDeviceUserAccessWritePages OBJECT-TYPE
    SYNTAX TchRgWebWizardSetup
    MAX-ACCESS read-only
    STATUS obsolete
    DESCRIPTION
        "Specifies the write access rights for every section of the WebWizard-Setup.
         The value of (1) means read-write, the value of (0) means read-only or no access.
         If a write access to a web page is enabled, read access is also enabled.
         The value of this objects is stored in non-vol.
         Default value after factory reset is 0xffffffff."
    ::= { tchRgDeviceUserAccess 5 }

tchRgDeviceUserAccessReadPages2 OBJECT-TYPE
    SYNTAX TchRgWebWizardSetup2
    MAX-ACCESS read-only
    STATUS obsolete
    DESCRIPTION
        "Specifies the read access rights for every section of the WebWizard-Setup.
         The value of (1) means read-only, the value of (0) means no-access.
         If a write access to a web page is enabled, read access is also enabled.
         The value of this objects is stored in non-vol.
         Default value after factory reset is 0x0fffffffffffffffffc0.
         This object applies to the new web pages."
    ::= { tchRgDeviceUserAccess 6 }

tchRgDeviceUserAccessWritePages2 OBJECT-TYPE
    SYNTAX TchRgWebWizardSetup2
    MAX-ACCESS read-only
    STATUS obsolete
    DESCRIPTION
        "Specifies the write access rights for every section of the WebWizard-Setup.
         The value of (1) means read-write, the value of (0) means read-only or no access.
         If a write access to a web page is enabled, read access is also enabled.
         The value of this objects is stored in non-vol.
         Default value after factory reset is 0x0fffffffffffffffffc0.
         This object applies to the new web pages."
    ::= { tchRgDeviceUserAccess 7 }

tchRgDevUserAccessUsername OBJECT-TYPE
    SYNTAX SnmpAdminString
    MAX-ACCESS read-write
    STATUS obsolete
    DESCRIPTION
        "Defines the username for user.
         This parameter is stored in non-vol and is blank by default."
    ::= { tchRgDeviceUserAccess 8 }

TchRgUserChangedFlag ::= TEXTUAL-CONVENTION
    STATUS       current
    DESCRIPTION
        "WebWizard Setup user changed flag sections.
        NOTE: Only Bits from 0-21 are supported for legacy web pages"
    SYNTAX BITS {
        lanParameters(0),
        wanMTU(1),
        wirelessBasic(2),
        wirelessAdvanced(3),
        wirelessSecurity(4),
        wirelessAccessControl(5),
        fixedCPE(6),
        ipMacPortFiltering(7),
        dmzHost(8),
        blockProxy(9),
        blockCookies(10),
        blockJava(11),
        blockActiveX(12),
        blockPopup(13),
        blockFragments(14),
        detectPortScan(15),
        detectFlood(16),
        firewallEvent(17),
        firewallProtection(18),
            ipsecPassthru(19),
            pptpPassthru(20),
            multicastPassthru(21),
        blockAnonymousIpWan(22),
        wanSetup(23),
        remoteMgmt(24),
        l2TP(25)
        }


tchRgDeviceConfiguration   OBJECT IDENTIFIER ::=  { tchRgDevice 4 }

tchRgDeviceConfigFilename OBJECT-TYPE
    SYNTAX SnmpAdminString
    MAX-ACCESS    read-write
    STATUS        current
    DESCRIPTION
        "Configuration filename from DHCP ACK."
    ::= { tchRgDeviceConfiguration 1 }

tchRgDeviceConfigStatus OBJECT-TYPE
    SYNTAX INTEGER {
        notSpecified(1),
        inProgress(2),
        success(3),
        errorServer(4),
        errorFileNotFound(5),
        errorBadFile(6),
        download(7)
        }
    MAX-ACCESS read-write
    STATUS current
    DESCRIPTION
        "Status of configuration file download.
         - notSpecified(1): DHCP ACK did not contain necessary information
         - inProgress(2): Configuration file is being downloaded
         - success(3): configuration file download completed successfully
         - errorServer(4): TFTP server did not respond
         - errorFileNotFound(5): no file on the server
         - errorBadFile(6): the file is not good, cannot be processed
         - download(7): commands the unit to download configuration file."
    ::= { tchRgDeviceConfiguration 2 }

tchRgDeviceUserChangedFlag OBJECT-TYPE
    SYNTAX TchRgUserChangedFlag
    MAX-ACCESS read-write
    STATUS current
    DESCRIPTION
       "Specifies which user changed flags are set. The value of (1) means
        that user changed flag value is set; the value of (0) means that
        the user changed flag is not set.
        The user changed flags are stored in non-vol.
        Default value after factory reset is 0x00000000
        NOTE: Legacy style web pages only support bits from 0-21
        "
    ::= { tchRgDeviceConfiguration 3 }

tchRgDeviceConfigSnmpEnable OBJECT-TYPE
    SYNTAX BITS {
        rgWan(0),
        rgDualIp(1),
                rgLanIp(2),
                rgPortForward(3)
    }
    MAX-ACCESS    read-write
    STATUS        current
    DESCRIPTION
        "Controls SNMP manager status on interfaces. If bit set to 0, the SNMP
         access is disabled. If bit set to 1, the SNMP access is enabled.
                 This MIB only applies to IPv4RG mode and is not relevant in
                 eRouter modes. "
    DEFVAL { { } }
    ::= { tchRgDeviceConfiguration 4 }

tchRgDeviceConfigIgnore  OBJECT-TYPE
    SYNTAX INTEGER {
        require(0),
        notRequire(1),
        notDownload(2)
        }
    MAX-ACCESS  read-only
    STATUS      current
    DESCRIPTION
        "This object controls if RG configuration file is to be downloaded.
         require(0): per specification, if DHCP contains parameters for the
                     file dowload, the RG MUST try to download it.
         notRequire(1): when config file download fails after exponential backoff,
                        RG will not retry DHCP and continue to be operational.
         notDownload(2): RG will not download config file.
         This MIB can be only in CM configuration file."
    DEFVAL { 0 }
    ::= { tchRgDeviceConfiguration 5 }
    
tchRgDeviceDefaultUIPasswordChanged  OBJECT-TYPE
    SYNTAX INTEGER {
        false(1),
        true(2)
        }
    MAX-ACCESS  read-only
    STATUS      current
    DESCRIPTION
        "This object provides information if the end user has changed Home USER web UI Password from default values or not.
        The MIB value is updated after CM boot up and when end user changes (clicks Save button) any Web UI settings.  
        false(1): End user has not yet changed the default Web UI Password.
        true (2): End user has changed the default Web UI Password.
        This MIB only considers Home User Web UI password. Changing advanced user Web UI password has no impact on this MIB. 
        This MIB is read only and the value is stored in nonvol."
         DEFVAL { 1 }
    ::= { tchRgDeviceConfiguration 6 }


tchRgDeviceTimeSetup   OBJECT IDENTIFIER ::=  { tchRgDevice 5 }

tchRgDeviceTimeSetupNtpEnabled OBJECT-TYPE
    SYNTAX TruthValue
    MAX-ACCESS read-write
    STATUS current
    DESCRIPTION
        "Stored in non-vol, disabled after factory reset."
    ::= { tchRgDeviceTimeSetup 1 }

tchRgDeviceTimeSetupNtpServerTable OBJECT-TYPE
       SYNTAX      SEQUENCE OF TchRgDeviceTimeSetupNtpServerEntry
       MAX-ACCESS  not-accessible
       STATUS      current
       DESCRIPTION
               "Up to 3 NTP servers are supported. This table
                is stored in non-vol. Default entries after factory
                reset are:
                1: time.nist.gov
                2: nist.aol-ca.truetime.com
                3: nist1-ny.glassey.com"
    ::= { tchRgDeviceTimeSetup 2 }

tchRgDeviceTimeSetupNtpServerEntry OBJECT-TYPE
    SYNTAX      TchRgDeviceTimeSetupNtpServerEntry
    MAX-ACCESS  not-accessible
    STATUS      current
    DESCRIPTION
            ""
    INDEX { tchRgDeviceTimeSetupNtpServerIndex }
    ::= { tchRgDeviceTimeSetupNtpServerTable 1 }

TchRgDeviceTimeSetupNtpServerEntry ::= SEQUENCE {
    tchRgDeviceTimeSetupNtpServerIndex      INTEGER,
    tchRgDeviceTimeSetupNtpServerAddress    SnmpAdminString
    }

tchRgDeviceTimeSetupNtpServerIndex OBJECT-TYPE
    SYNTAX      INTEGER (1..3)
    MAX-ACCESS  not-accessible
    STATUS      current
    DESCRIPTION
            "The index"
    ::= { tchRgDeviceTimeSetupNtpServerEntry 1 }

tchRgDeviceTimeSetupNtpServerAddress OBJECT-TYPE
    SYNTAX      SnmpAdminString
    MAX-ACCESS  read-write
    STATUS      current
    DESCRIPTION
            "IP address or FQDN of the NTP server."
    ::= { tchRgDeviceTimeSetupNtpServerEntry 2 }

tchRgDeviceTimeSetupZone OBJECT-TYPE
    SYNTAX TchRgTimeZone
    MAX-ACCESS read-write
    STATUS current
    DESCRIPTION
        "Time zone for the gateway.
         Stored in non-vol, gmtZeroDublinEdinburghLisbonLondon(26)
         after factory reset."
    ::= { tchRgDeviceTimeSetup 3 }

tchRgDeviceTimeSetupDst OBJECT-TYPE
    SYNTAX INTEGER (0..120)
    UNITS "Minutes"
    MAX-ACCESS read-write
    STATUS current
    DESCRIPTION
        "Daylight saving time. If set to 0, DST is disabled
         Stored in non-vol, 0 after factory reset."
    ::= { tchRgDeviceTimeSetup 4 }


-- Login control table - obsolete

tchRgDeviceLoginControlTable OBJECT-TYPE
       SYNTAX      SEQUENCE OF TchRgDeviceLoginControlEntry
       MAX-ACCESS  not-accessible
       STATUS      obsolete
       DESCRIPTION
               "Rules of accessing Setup RG configuration section by user and operator."
    ::= { tchRgDevice 6 }


tchRgDeviceLoginControlEntry OBJECT-TYPE
    SYNTAX      TchRgDeviceLoginControlEntry
    MAX-ACCESS  not-accessible
    STATUS      obsolete
    DESCRIPTION
            "List of rules of accessing Setup RG configuration section of WebWizard"
    INDEX { ifIndex, tchRgDeviceLoginControlName }
    ::= { tchRgDeviceLoginControlTable 1 }

TchRgDeviceLoginControlEntry ::= SEQUENCE {
    tchRgDeviceLoginControlName  INTEGER,
    tchRgDeviceLoginControlState INTEGER
    }

tchRgDeviceLoginControlName OBJECT-TYPE
    SYNTAX INTEGER {
        user(1),
        operator(2)
        }
    MAX-ACCESS  not-accessible
    STATUS      obsolete
    DESCRIPTION
            ""
    ::= { tchRgDeviceLoginControlEntry 1 }

tchRgDeviceLoginControlState OBJECT-TYPE
    SYNTAX INTEGER  {
        disable(0),
        enable(2)
        }
    MAX-ACCESS  read-only
    STATUS      obsolete
    DESCRIPTION
            "Control user and operator access to Setup RG configuration page per interface."
    ::= { tchRgDeviceLoginControlEntry 2 }


-- MIBs to poll IANA / PD info for eRouter interface

tchRgDeviceIanaContent   OBJECT IDENTIFIER ::=  { tchRgDevice 7 }

tchRgDeviceIanaIAID OBJECT-TYPE
        SYNTAX Unsigned32
        MAX-ACCESS read-only
        STATUS current
        DESCRIPTION
                "Returns the IAID value embedded in the IA_NA for the
eRouter's DHCPv6 lease."
        ::= { tchRgDeviceIanaContent 1 }

tchRgDeviceIanaT1 OBJECT-TYPE
        SYNTAX Integer32
        MAX-ACCESS read-only
        STATUS current
        DESCRIPTION
                "Returns the T1 value embedded in the IA_NA for the eRouter's
DHCPv6 lease."
        ::= { tchRgDeviceIanaContent 2 }

tchRgDeviceIanaT2 OBJECT-TYPE
        SYNTAX Integer32
        MAX-ACCESS read-only
        STATUS current
        DESCRIPTION
                "Returns the T2 value embedded in the IA_NA for the eRouter's
DHCPv6 lease."
        ::= { tchRgDeviceIanaContent 3 }

tchRgDeviceIanaTable OBJECT-TYPE
        SYNTAX SEQUENCE OF TchRgDeviceIanaEntry
        MAX-ACCESS not-accessible
        STATUS current
        DESCRIPTION
                "Table of IA Address entries associated with IA_NA for the
eRouter's DHCPv6 lease."
        ::= { tchRgDeviceIanaContent 4 }

tchRgDeviceIanaEntry OBJECT-TYPE
    SYNTAX      TchRgDeviceIanaEntry
    MAX-ACCESS  not-accessible
    STATUS      current
    DESCRIPTION
            "Table of IA Address entries associated with IA_NA for the
eRouter's DHCPv6 lease."
    INDEX { tchRgDeviceIanaIndex }
    ::= { tchRgDeviceIanaTable 1 }

TchRgDeviceIanaEntry ::= SEQUENCE {
    tchRgDeviceIanaIndex              INTEGER,
    tchRgDeviceIanaValue              InetAddress,
    tchRgDeviceIanaPreferredLifetime  Integer32,
    tchRgDeviceIanaValidLifetime      Integer32
    }

tchRgDeviceIanaIndex OBJECT-TYPE
    SYNTAX      INTEGER (1..4)
    MAX-ACCESS  not-accessible
    STATUS      current
    DESCRIPTION
            "The index"
    ::= { tchRgDeviceIanaEntry 1 }

tchRgDeviceIanaValue OBJECT-TYPE
    SYNTAX      InetAddress
    MAX-ACCESS  read-only
    STATUS      current
    DESCRIPTION
            "IPv6 address provided to the eRouter WAN interface via DHCPv6."
    ::= { tchRgDeviceIanaEntry 2 }

tchRgDeviceIanaPreferredLifetime OBJECT-TYPE
    SYNTAX      Integer32
    MAX-ACCESS  read-only
    STATUS      current
    DESCRIPTION
            "Preferred Lifetime setting for an IPv6 address assigned to the
eRouter."
    ::= { tchRgDeviceIanaEntry 3 }

tchRgDeviceIanaValidLifetime OBJECT-TYPE
    SYNTAX      Integer32
    MAX-ACCESS  read-only
    STATUS      current
    DESCRIPTION
            "Valid Lifetime setting for an IPv6 address assigned to the
eRouter."
    ::= { tchRgDeviceIanaEntry 4 }



tchRgDeviceIapdContent   OBJECT IDENTIFIER ::=  { tchRgDevice 8 }

tchRgDeviceIapdIAID OBJECT-TYPE
        SYNTAX Unsigned32
        MAX-ACCESS read-only
        STATUS current
        DESCRIPTION
                "Returns the IAID value embedded in the IA_PD for the
eRouter's DHCPv6 lease."
        ::= { tchRgDeviceIapdContent 1 }

tchRgDeviceIapdT1 OBJECT-TYPE
        SYNTAX Integer32
        MAX-ACCESS read-only
        STATUS current
        DESCRIPTION
                "Returns the T1 value embedded in the IA_PD for the eRouter's
DHCPv6 lease."
        ::= { tchRgDeviceIapdContent 2 }

tchRgDeviceIapdT2 OBJECT-TYPE
        SYNTAX Integer32
        MAX-ACCESS read-only
        STATUS current
        DESCRIPTION
                "Returns the T2 value embedded in the IA_PD for the eRouter's
DHCPv6 lease."
        ::= { tchRgDeviceIapdContent 3 }

tchRgDeviceIapdTable OBJECT-TYPE
        SYNTAX SEQUENCE OF TchRgDeviceIapdEntry
        MAX-ACCESS not-accessible
        STATUS current
        DESCRIPTION
                "Table of IA Prefix entries associated with IA_PD for the
eRouter's DHCPv6 lease."
        ::= { tchRgDeviceIapdContent 4 }

tchRgDeviceIapdEntry OBJECT-TYPE
    SYNTAX      TchRgDeviceIapdEntry
    MAX-ACCESS  not-accessible
    STATUS      current
    DESCRIPTION
            "Table of IA Address entries associated with IA_PD for the
eRouter's DHCPv6 lease."
    INDEX { tchRgDeviceIapdIndex }
    ::= { tchRgDeviceIapdTable 1 }

TchRgDeviceIapdEntry ::= SEQUENCE {
    tchRgDeviceIapdIndex              INTEGER,
    tchRgDeviceIapdPreferredLifetime  Integer32,
    tchRgDeviceIapdValidLifetime      Integer32,
    tchRgDeviceIapdPrefixLength       INTEGER,
    tchRgDeviceIapdPrefixValue        InetAddress
    }

tchRgDeviceIapdIndex OBJECT-TYPE
    SYNTAX      INTEGER (1..4)
    MAX-ACCESS  not-accessible
    STATUS      current
    DESCRIPTION
            "The index"
    ::= { tchRgDeviceIapdEntry 1 }

tchRgDeviceIapdPreferredLifetime OBJECT-TYPE
    SYNTAX      Integer32
    MAX-ACCESS  read-only
    STATUS      current
    DESCRIPTION
            "Preferred Lifetime setting for an IPv6 address assigned to the
eRouter."
    ::= { tchRgDeviceIapdEntry 2 }

tchRgDeviceIapdValidLifetime OBJECT-TYPE
    SYNTAX      Integer32
    MAX-ACCESS  read-only
    STATUS      current
    DESCRIPTION
            "Valid Lifetime setting for an IPv6 address assigned to the
eRouter."
    ::= { tchRgDeviceIapdEntry 3 }

tchRgDeviceIapdPrefixLength OBJECT-TYPE
        SYNTAX          INTEGER
        MAX-ACCESS      read-only
        STATUS          current
        DESCRIPTION
                "Length (in bits) for this prefix."
        ::= { tchRgDeviceIapdEntry 4 }

tchRgDeviceIapdPrefixValue OBJECT-TYPE
        SYNTAX          InetAddress
        MAX-ACCESS      read-only
        STATUS          current
        DESCRIPTION
                "Prefix address specified in the IA_PD."
        ::= { tchRgDeviceIapdEntry 5 }



-- ******************
-- ***** 802.11 *****
-- ******************

tchRgDot11 OBJECT IDENTIFIER ::=  { tchRg 2 }


-- *************************
-- GENERAL AND CHANNEL SETUP
-- *************************

tchRgDot11MgmtBase OBJECT IDENTIFIER ::= { tchRgDot11 1 }

tchRgDot11OperMode OBJECT-TYPE
    SYNTAX      INTEGER {
                notAvailable(0),
                off(1),
                remote(2),
                local(3)
    }
    MAX-ACCESS  read-write
    STATUS      current
    DESCRIPTION
        "Used to control the 802.11 operational mode. If set to
         notAvailable(0), then the wireless interface will be disabled, with
         the radio off, and no wireless settings web pages will be available to
         the user.
         If set to off(1) then the wireless interface will be disabled, but
         there may be a web page present which indicates that wireless service
         is available and that the MSO should be contacted to enable it.
         If set to remote(2), then the wireless interface will be enabled, but
         the configuration web pages are read-only so that the user may not
         change the settings.
         If set to local(3), then the wireless interface will be enabled, and
         the web pages will be read-write so that the user has full control over
         the settings.
         This parameter is stored in non-vol and set to local(3) after factory
         reset."
    ::= { tchRgDot11MgmtBase 1 }

tchRgDot11CurrentChannel OBJECT-TYPE
    SYNTAX      Unsigned32 (0..216)
    MAX-ACCESS  read-write
    STATUS      current
    DESCRIPTION
        "Controls and reflects the current channel number.
         The value of 0 means auto channel selection.
         This parameter is stored in non-vol and is 0
         after factory reset.

         For 802.11b/g/n modes in 2.4 GHz, the available channels are 1-14.
         For 802.11a/n modes in 5 GHz, the available channels are 34-216.
         Channel selection is subjected to restrictions based on Wifi
         Country Code"
    ::= { tchRgDot11MgmtBase 3 }

tchRgDot11BeaconInterval OBJECT-TYPE
    SYNTAX      Unsigned32  (1..65535)
    UNITS       "milliseconds"
    MAX-ACCESS  read-write
    STATUS      current
    DESCRIPTION
        "Controls and reflects the beacon interval for the device.
         This parameter is stored in non-vol."
    ::= { tchRgDot11MgmtBase 4 }

tchRgDot11DTIMInterval OBJECT-TYPE
    SYNTAX      Unsigned32  (1..255)
    UNITS       "milliseconds"
    MAX-ACCESS  read-write
    STATUS      current
    DESCRIPTION
        "Controls and reflects the DTIM interval for the device.
         This parameter is stored in non-vol."
    ::= { tchRgDot11MgmtBase 5 }

-- Renamed from tchRgDot11FragmentationThreshold to avoid conflict w/ IEEE 802.11 MIB
tchRgDot11FragThresh OBJECT-TYPE
    SYNTAX      Unsigned32  (256..2346)
    UNITS       "bytes"
    MAX-ACCESS  read-write
    STATUS      current
    DESCRIPTION
        "Controls and reflects the fragmentation threshold for the device.
         This parameter is stored in non-vol."
    ::= { tchRgDot11MgmtBase 6 }

-- Renamed from tchRgDot11RTSThreshold to avoid conflict w/ IEEE 802.11 MIB
tchRgDot11RTSThresh OBJECT-TYPE
    SYNTAX      Unsigned32  (0..2347)
    MAX-ACCESS  read-write
    STATUS      current
    DESCRIPTION
        "Controls and reflects the RTS threshold for the device.
         This parameter is stored in non-vol."
    ::= { tchRgDot11MgmtBase 7 }


-- Renamed from tchRgDot11ShortRetryLimit to avoid conflict w/ IEEE 802.11 MIB
tchRgDot11SRL OBJECT-TYPE
    SYNTAX      Unsigned32  (1..255)
    MAX-ACCESS  read-write
    STATUS      current
    DESCRIPTION
        "Controls and reflects the short retry limit for the device.
         This parameter is stored in non-vol."
    ::= { tchRgDot11MgmtBase 8 }

-- Renamed from tchRgDot11LongRetryLimit to avoid conflict w/ IEEE 802.11 MIB
tchRgDot11LRL OBJECT-TYPE
    SYNTAX      Unsigned32  (1..255)
    MAX-ACCESS  read-write
    STATUS      current
    DESCRIPTION
        "Controls and reflects the long retry limit for the device.
         This parameter is stored in non-vol."
    ::= { tchRgDot11MgmtBase 9 }

tchRgDot1154gNetMode OBJECT-TYPE
    SYNTAX INTEGER {
        only11g(4),
        maxCompatibility(5)
        }
    MAX-ACCESS  read-write
    STATUS      obsolete
    DESCRIPTION
        "Controls and reflects the behavior of the device with regards to which
         flavor of 802.11 is used.  If set to maxCompatibility(5), the device
         will interoperate with the widest variety of 54g and 802.11b clients.
         If set to only11g(4), only 54g clients will be accepted.
         Note that this MIB should be enabled only in 2.4GHz.

         This parameter is stored in non-vol and is set to maxCompatibility(5)
         after factory reset."
    ::= { tchRgDot11MgmtBase 10 }

tchRgDot1154gProtectionEnable OBJECT-TYPE
    SYNTAX      TruthValue
    MAX-ACCESS  read-write
    STATUS      current
    DESCRIPTION
        "Controls and reflects the state of 54g protection.  If set to true(1),
         the AP will use RTS/CTS to improve 802.11g performance in mixed
         802.11g/802.11b networks.  Set to false(2) to maximize 802.11g
         throughput under most conditions.
         Note that this MIB should be enabled only in 2.4GHz.
         This parameter is stored in non-vol."
    ::= { tchRgDot11MgmtBase 11 }

tchRgDot11Rate OBJECT-TYPE
    SYNTAX      INTEGER {
                auto(0),
                mbits1(1),
                mbits2(2),
                mbits5-5(5),
                mbits6(6),
                mbits9(9),
                mbits11(11),
                mbits12(12),
                mbits18(18),
                mbits24(24),
                mbits36(36),
                mbits48(48),
                mbits54(54)
    }
    MAX-ACCESS  read-write
    STATUS      current
    DESCRIPTION
        "Forces the transmission rate for the AP to a particular speed.
         Note that the 802.11b rates, including mbits1(1), mbits2(2),
         mbits5-5(5), and mbits11(11), are not available in 5GHz.
         This parameter is stored in non-vol."
    ::= { tchRgDot11MgmtBase 12 }

tchRgDot11OutputPower OBJECT-TYPE
    SYNTAX      INTEGER {
                percent25(25),
                percent50(50),
                percent75(75),
                percent100(100)
    }
    MAX-ACCESS  read-write
    STATUS      current
    DESCRIPTION
        "Sets the output power relative to the hardware's maximum capability.
         This parameter is stored in non-vol."
    ::= { tchRgDot11MgmtBase 13 }

tchRgDot11Country OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements.
         This parameter is stored in non-vol and is worldWide(0)
         (channels 1-11) after factory reset."
    ::= { tchRgDot11MgmtBase 14 }

tchRgDot11Antenna OBJECT-TYPE
    SYNTAX  INTEGER {
        disableIntTx(0),
        enableIntTx(1)
        }
    MAX-ACCESS  read-write
    STATUS      current
    DESCRIPTION
        "This parameter is stored in non-vol and set to
         disableIntTx(0) after factory reset."
    ::= { tchRgDot11MgmtBase 15 }

tchRgDot11MbssUserControl OBJECT-TYPE
    SYNTAX INTEGER (1..8|65536..16711680)
    MAX-ACCESS read-write
    STATUS current
    DESCRIPTION
        "Sets the number of user controlled Wifi networks via web pages.
         1: The user has control over the primary wireless network only.
            No guest network page is displayed.
         2: The user has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit Mask Control:
         Bit 16: -- User has control over Primary Wireless Network               :  65536
         Bit 17: -- User has control over Guest Network 1 (interface 33) : 131072
         Bit 18: -- User has control over Guest Network 2 (interface 34) : 262144
         Bit 19: -- User has control over Guest Network 3 (interface 35) : 524288
         Bit 20: -- User has control over Guest Network 4 (interface 36) :1048576
         Bit 21: -- User has control over Guest Network 5 (interface 37) :2097152
         Bit 22: -- User has control over Guest Network 6 (interface 38) :4194304
         Bit 23: -- User has control over Guest Network 7 (interface 39) :8388608

         This object value is stored in non-vol and set to 1
         after factory reset."
    ::= { tchRgDot11MgmtBase 16 }

tchRgDot11MbssUseNonvol OBJECT-TYPE
    SYNTAX TruthValue
    MAX-ACCESS read-write
    STATUS current
    DESCRIPTION
        "Allows to save additional BSS parameters to non-vol if set to true.
         Primary BSS parameters are ALWAYS stored in non-vol.
         This object value is stored in non-vol and set to false
         after factory reset."
    ::= { tchRgDot11MgmtBase 17 }

tchRgDot11MbssAdminControl OBJECT-TYPE
    SYNTAX INTEGER (1..8|65536..16711680)
    MAX-ACCESS read-write
    STATUS current
    DESCRIPTION
        "Sets the number of admin controlled Wifi networks via web pages.
         1: The admin has control over the primary wireless network only.
            No guest network page is displayed.
         2: The admin has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit 16: -- Admin Has control over Primary Wireless Network               :  65536
         Bit 17: -- Admin Has control over Guest Network 1 (interface 33) : 131072
         Bit 18: -- Admin Has control over Guest Network 2 (interface 34) : 262144
         Bit 19: -- Admin Has control over Guest Network 3 (interface 35) : 524288
         Bit 20: -- Admin Has control over Guest Network 4 (interface 36) :1048576
         Bit 21: -- Admin Has control over Guest Network 5 (interface 37) :2097152
         Bit 22: -- Admin Has control over Guest Network 6 (interface 38) :4194304
         Bit 23: -- Admin Has control over Guest Network 7 (interface 39) :8388608

         This object value is stored in non-vol and set to 1
         after factory reset."

    ::= { tchRgDot11MgmtBase 18 }

tchRgDot11ActualChannel OBJECT-TYPE
    SYNTAX      INTEGER
    MAX-ACCESS  read-only
    STATUS      current
    DESCRIPTION
        "Reports the current channel number that wireless is on.
         The value of 0 means wireless is disabled."
    ::= { tchRgDot11MgmtBase 19 }

tchRgDot11OnOffPushButtonTime OBJECT-TYPE
    SYNTAX      INTEGER (0..11)
    UNITS       "seconds"
    MAX-ACCESS  read-write
    STATUS      current
    DESCRIPTION
        "Specifies how long to press WPS button to enable or disable
         the WiFi interface (primary SSID). When set to 11, the feature
         is disabled.
         Stored in non-vol, 11 after factory reset."
    ::= { tchRgDot11MgmtBase 20 }

tchRgDot11Wmm OBJECT-TYPE
    SYNTAX  INTEGER {
        disable(0),
        enable(1)
        }
    MAX-ACCESS  read-write
    STATUS      current
    DESCRIPTION
        "Mib to Enable/Disable Wifi-Multi Media (WMM) QOS fetures.
        This parameter is stored in non-vol and set to
        enable(1) after a factory reset."
    DEFVAL { 1 }
    ::= { tchRgDot11MgmtBase 21 }

 tchRgDot11WmmNoAck OBJECT-TYPE
    SYNTAX  INTEGER {
        disable(0),
        enable(1)
        }
    MAX-ACCESS  read-write
    STATUS      current
    DESCRIPTION
        "Mib to control whether Wifi packets require acknowledgement.
        disable(0) Use acknowledgemnet for Wifi packets.
        enable(1)  Sets No acknowledgement which allows for higher throughput and lower latency when some
                   packetloss is acceptable (ex. VoIP).
        Note: If WMM is disabled then this setting has no effect, and you can Not disable Acks from being
        returned from the stations.
        This parameter is stored in non-vol and set to disable(0) after a factory reset."
    DEFVAL { 0 }
    ::= { tchRgDot11MgmtBase 22 }

 tchRgDot11MulticastRate OBJECT-TYPE
    SYNTAX      INTEGER {
                                disable(0),
                mbits1(1),
                mbits2(2),
                mbits5-5(5),
                mbits6(6),
                mbits9(9),
                mbits11(11),
                mbits12(12),
                mbits18(18),
                mbits24(24),
                mbits36(36),
                mbits48(48),
                mbits54(54)
        }
    UNITS       "Mbps"
    MAX-ACCESS  read-write
    STATUS      current
    DESCRIPTION
        "Forces the dot11 multicast Phy transmission rate.
         Note that the 802.11b rates, including mbits1(1), mbits2(2),
         mbits5-5(5), and mbits11(11), are not available in 5GHz.
         This object is stored in non-vol and defaults to disable(0) after factory reset."
    DEFVAL { 0 }
    ::= { tchRgDot11MgmtBase 23 }

tchRgDot11WirelessButtonOperation OBJECT-TYPE
    SYNTAX  INTEGER {
        disable(0),
        enable(1)
    }
    MAX-ACCESS    read-write
    STATUS        current
    DESCRIPTION
        "To enable or disable the button press of wireless ON/OFF button.
                  This feature will work only on products that has the wireless ON/OFF button.
                  This MIB will control if the Wireless ON/OFF button can be pressed or not.
                  If it is enable then button press would take effect otherwise there will not be any effect on button press.
                  By default value will be set to enable(1)."
    DEFVAL { 1 }
    ::= { tchRgDot11MgmtBase 24 }

tchRgDot11ChannelSelectionPolicy OBJECT-TYPE
    SYNTAX  INTEGER {
        default(0),
        legacy(1),
                intf(2),
                intfbusy(3),
                optimized(4)
    }
    MAX-ACCESS    read-write
    STATUS        current
    DESCRIPTION
        "Mib to select Auto Channel Selection policy.
                default(0): By default the number of APs and the Composite Noise Score is used to decide the best channel available to the radio.
        legacy(1): Only considers number of APs.
                intf(2): Only considers number of APs and interference measurement.
                intfbusy(3): Considers interference and channel occupancy (including number of APs).
                optimized(4): Considers interference (including back ground noise), channel occupancy (including number of APs) and Tx power.
                This parameter is stored in non-vol and set to default(0) after a factory reset."
    DEFVAL { 0 }
    ::= { tchRgDot11MgmtBase 25 }
-- =====================
-- WiFi Scan results
-- =====================

tchRgDot11ApsScan OBJECT IDENTIFIER ::= { tchRgDot11MgmtBase 26 }

tchRgDot11ApsScanEnable OBJECT-TYPE
    SYNTAX      TruthValue
    MAX-ACCESS  read-write
    STATUS      current
    DESCRIPTION
        "If set to true(1), WiFi Radio will be configured to scan for the APs.
        Scan results with list of neighboring APs will be updated in tchRgDot11ApsScanResultsTable.
        Always returns false(2) when read."
    ::= { tchRgDot11ApsScan 1 }


tchRgDot11ApsScanResultsTable  OBJECT-TYPE
    SYNTAX      SEQUENCE OF TchRgDot11ApsScanResultsEntry
    MAX-ACCESS  not-accessible
    STATUS      current
    DESCRIPTION
        "A table of neighboring APs list found after APs Scan request (tchRgDot11ApsScan).
        The table can list up to 32 number of APs."
    ::= { tchRgDot11ApsScan 2 }

tchRgDot11ApsScanResultsEntry OBJECT-TYPE
    SYNTAX      TchRgDot11ApsScanResultsEntry
    MAX-ACCESS  not-accessible
    STATUS      current
    DESCRIPTION
        "An entry describing neighboring AP information. First element wifiValid
        determines if the current entry is valid or not. The information includes
        SSID, RSSI, Channel, Mac Address etc."
    INDEX   { ifIndex }
    ::= { tchRgDot11ApsScanResultsTable 1  }

TchRgDot11ApsScanResultsEntry ::=
    SEQUENCE    {
        tchRgDot11ApsScanValid           INTEGER,
        tchRgDot11ApsScanNetworkName     OCTET STRING,
        tchRgDot11ApsScanSecurityMode    OCTET STRING,
        tchRgDot11ApsScanPhyMode         OCTET STRING,
        tchRgDot11ApsScanRssi            INTEGER,
        tchRgDot11ApsScanChannel         INTEGER,
        tchRgDot11ApsScanMacAddress      PhysAddress
    }

tchRgDot11ApsScanValid OBJECT-TYPE
    SYNTAX      INTEGER {
                invalid(0),
                valid(1)
    }
    MAX-ACCESS  read-only
    STATUS      current
    DESCRIPTION
        "Determines if the current entry is valid or not."
    ::= { tchRgDot11ApsScanResultsEntry 1 }

tchRgDot11ApsScanNetworkName OBJECT-TYPE
    SYNTAX      OCTET STRING
    MAX-ACCESS  read-only
    STATUS      current
    DESCRIPTION
        "Neighboring AP name or SSID."
    ::= { tchRgDot11ApsScanResultsEntry 2 }

tchRgDot11ApsScanSecurityMode OBJECT-TYPE
    SYNTAX      OCTET STRING
    MAX-ACCESS  read-only
    STATUS      current
    DESCRIPTION
        "Neighboring AP security mode."
    ::= { tchRgDot11ApsScanResultsEntry 3 }

tchRgDot11ApsScanPhyMode OBJECT-TYPE
    SYNTAX      OCTET STRING
    MAX-ACCESS  read-only
    STATUS      current
    DESCRIPTION
        "Neighboring AP PHY mode."
    ::= { tchRgDot11ApsScanResultsEntry 4 }

tchRgDot11ApsScanRssi OBJECT-TYPE
    SYNTAX      INTEGER
    MAX-ACCESS  read-only
    STATUS      current
    DESCRIPTION
        "Neighboring AP receive signal strenth."
    ::= { tchRgDot11ApsScanResultsEntry 5 }

tchRgDot11ApsScanChannel OBJECT-TYPE
    SYNTAX      INTEGER
    MAX-ACCESS  read-only
    STATUS      current
    DESCRIPTION
        "Neighboring AP operating channel."
    ::= { tchRgDot11ApsScanResultsEntry 6 }

tchRgDot11ApsScanMacAddress OBJECT-TYPE
    SYNTAX      PhysAddress
    MAX-ACCESS  read-only
    STATUS      current
    DESCRIPTION
        "Neighboring AP MAC address."
    ::= { tchRgDot11ApsScanResultsEntry 7 }

tchRgDot11ACSExcludeTable  OBJECT-TYPE
    SYNTAX      SEQUENCE OF TchRgDot11ACSExcludeEntry
    MAX-ACCESS  not-accessible
    STATUS      current
    DESCRIPTION
        "AcsBlacklist table"
    ::= { tchRgDot11MgmtBase 27 }

tchRgDot11ACSExcludeEntry OBJECT-TYPE
    SYNTAX      TchRgDot11ACSExcludeEntry
    MAX-ACCESS  not-accessible
    STATUS      current
    DESCRIPTION
        "A row in the table represents channel blacklist parameters for each Radio."
    INDEX   { ifIndex }
    ::= { tchRgDot11ACSExcludeTable 1 }

TchRgDot11ACSExcludeEntry ::=
    SEQUENCE {
         tchRgDot11ACSExcludeChannels          OCTET STRING
    }
	
tchRgDot11ACSExcludeChannels OBJECT-TYPE
    SYNTAX      OCTET STRING (SIZE(0..256))
    MAX-ACCESS  read-write
    STATUS      current
    DESCRIPTION
        "Set/Gets the channels (seperated by comma) that ACSD scan should exclude"
    ::= {  tchRgDot11ACSExcludeEntry 1 }


tchRgDot11SromCalibration  OBJECT-TYPE
    SYNTAX      INTEGER {
                emea(0),
                latam(1),
                other(2)
    }
    MAX-ACCESS read-only
    STATUS current
    DESCRIPTION
        "MIB to return the value of CGA2121 WIFI calibration SROM data. 
		  (0) is for EMEA calibration, 
		  (1) is for LATAM calibration, 
		  (2) is for other. 
		  CGA2121TCH (EMEA) products should always return a value of 0. 
		  CGA2121TCH2 and other LATAM variants should always return a value of 1."
    ::= { tchRgDot11MgmtBase 28 }


tchRgDot11SromCalibrationChanged OBJECT-TYPE
      SYNTAX INTEGER{
            false(0),
            true(1),
            error(2)}
      MAX-ACCESS read-only
      STATUS current
      DESCRIPTION
            "MIB to know if value of CGA2121 WIFI calibration SROM data has been changed.
            false (0): WIFI calibration SROM data has not been changed.
            true (1): WIFI calibration SROM data has been changed successfully.
            error (2): WIFI calibration SROM data must be changed, but writing operation failed."
      DEFVAL { 0 }
      ::= { tchRgDot11MgmtBase 29 }


-- =====================
-- PER BSS CONFIGURATION
-- =====================
-- The interface numbers are:
-- 32: SSID1 + LAN
-- 33: SSID2
-- 34: SSID3
-- 35: SSID4
-- 36: SSID5
-- 37: SSID6
-- 38: SSID7
-- 39: SSID8


tchRgDot11Bss OBJECT IDENTIFIER ::= { tchRgDot11 2 }


tchRgDot11BssTable  OBJECT-TYPE
    SYNTAX      SEQUENCE OF TchRgDot11BssEntry
    MAX-ACCESS  not-accessible
    STATUS      current
    DESCRIPTION
        "BSS table"
    ::= { tchRgDot11Bss 1 }

tchRgDot11BssEntry OBJECT-TYPE
    SYNTAX      TchRgDot11BssEntry
    MAX-ACCESS  not-accessible
    STATUS      current
    DESCRIPTION
        "A row in the table which represents parameters for SSID."
    INDEX   { ifIndex }
    ::= { tchRgDot11BssTable 1 }

TchRgDot11BssEntry ::=
    SEQUENCE {
        tchRgDot11BssId            PhysAddress,
        tchRgDot11BssEnable        INTEGER,
        tchRgDot11BssSsid          OCTET STRING,
        tchRgDot11BssSecurityMode  INTEGER,
        tchRgDot11BssClosedNetwork TruthValue,
        tchRgDot11BssAccessMode    INTEGER,
        tchRgDot11BssLanAccess     INTEGER,
        tchRgDot11BssDsBwReserve   INTEGER,
        tchRgDot11BssDsBwPriority  INTEGER,
        tchRgDot11BssMaxNumSta     INTEGER,
        tchRgDot11BssCountStaAsCpe TruthValue,
        tchRgDot11BssUserStatus    INTEGER,
        tchRgDot11BssHotSpot       TruthValue,
        tchRgDot11BssApIsolation   INTEGER,
        tchRgDot11BssSecSsidTrafficPriority  INTEGER,
        tchRgDot11BssRejectPriSsidSta        TruthValue,
        tchRgDot11BssRejectPriSsidStaCount   INTEGER,
        tchRgDot11BssFactoryResetSSID        TruthValue,
        tchRgDot11BssPMFcontrol              INTEGER,
        tchRgDot11BssTostagging              INTEGER
        }

tchRgDot11BssId OBJECT-TYPE
    SYNTAX      PhysAddress
    MAX-ACCESS  read-only
    STATUS      current
    DESCRIPTION
        "Returns the BSSID"
    ::= { tchRgDot11BssEntry 1 }

tchRgDot11BssEnable OBJECT-TYPE
    SYNTAX INTEGER {
        enable(1),
        disable(2),
        enableOnline(3)
        }
    MAX-ACCESS  read-write
    STATUS      current
    DESCRIPTION
        "Controls the BSS state.
         When set to enableOnline(3), the SSID is enabled only
         when the cable modem is online. When the modem changes
         state to offline, the AP will send dissasociation messages
         to the STAs connected to the SSID and then disable.
         The value of primary BSS is stored in non-vol and is enabled(1)
         after factory reset.
         The other BSSs are disabled by default. If other
         BSS's SSID name is not defined, the BSS will not
         be enabled."
    ::= { tchRgDot11BssEntry 2 }

tchRgDot11BssSsid OBJECT-TYPE
    SYNTAX      OCTET STRING (SIZE(0..32))
    MAX-ACCESS  read-write
    STATUS      current
    DESCRIPTION
        "Controls and reflects the service set identifier.
         The value of primary BSS is stored in non-vol and is
         empty after factory reset.
         If other BSS's SSID name is not defined, the BSS
         will not be enabled."
    ::= { tchRgDot11BssEntry 3 }

tchRgDot11BssSecurityMode OBJECT-TYPE
    SYNTAX INTEGER {
        disabled(0),
        wep(1),
        wpaPsk(2),
        wpa2Psk(3),
        wpaEnterprise(4),
        wpa2Enterprise(5),
        --radiusWep(6)
        wpaWpa2Psk(7),
        wpaWpa2Enterprise(8)
        }
    MAX-ACCESS  read-write
    STATUS      current
    DESCRIPTION
        "Secrity for BSS.
         Beacause WPA2 is backwords compatible with WPA, setting this
         object to wpaWpa2Psk(7) is allowed and has the same effect as
         setting to wpa2Psk(3). The same is true for wpaWpa2Enterprise(8)
         and wpa2Enterprise(5).
         The value for primary BSS is stored in non-vol and is wpaWpa2Psk(7)
         after factory reset.
         For each other BSS security has to be included in configuration
         file or the BSS will be disabled."
    ::= { tchRgDot11BssEntry 4 }

tchRgDot11BssClosedNetwork OBJECT-TYPE
    SYNTAX      TruthValue
    MAX-ACCESS  read-write
    STATUS      current
    DESCRIPTION
        "Controls whether the device will operate in closed network mode.  If
         set to true(1), then the network mode is closed and the SSID will not
         be broadcast in beacon packets.  If set to false(2), then the network
         mode is open and the SSID will be broadcast in beacon packets.
         The value for primary BSS is stored in non-vol.
         The default value for other BSSs is false."
    ::= { tchRgDot11BssEntry 5 }

tchRgDot11BssAccessMode OBJECT-TYPE
    SYNTAX      INTEGER {
                allowAny(0),
                allowList(1),
                denyList(2)
    }
    MAX-ACCESS  read-write
    STATUS      current
    DESCRIPTION
        "Controls what stations will be given access to the device.  If set to
         allowAny(0), then any station will be allowed to connect.  If set
         to allowList(1), then only stations whose MAC address appears in
         the tchRgDot11AccessMacTable will be allowed to connect.
         The value for primary BSS is stored in non-vol.
         The default value for other BSSs is 0."
    ::= { tchRgDot11BssEntry 6 }

-- not implemented
tchRgDot11BssLanAccess OBJECT-TYPE
    SYNTAX INTEGER {
        lan(1),
        guest(2)
        }
    MAX-ACCESS read-write
    STATUS current
    DESCRIPTION
        "If set to lan(1), this service set will be authorized as a member of
         the local area network.  If set to guest(2), this service set will
         have access to the wide area internet, but will have restricted access
         to the local area network.
         Default values are lan(1) for the primary BSS and guest(2) for other BSSs.
         NOTE: NOT IMPLEMENTED"
    ::= { tchRgDot11BssEntry 8 }

tchRgDot11BssDsBwReserve OBJECT-TYPE
    SYNTAX INTEGER
    UNITS "Bps"
    MAX-ACCESS  read-write
    STATUS      current
    DESCRIPTION
        "Controls the downstream (from AP to client) throughput
         in Bytes per second from AP to client on a BSS.
         This object reserves the throughput for a BSS. The rest of
         leftover bandwidth is assigned based on BSS priority.
         Note: if the reserved bandwidth is not used, it is shared
         with other BSSs based on their priority.
         If set to 0 there is no reservation.

         Example:
         BSS 1, 2 and 3 have reservation of 3Mb/s each. BSS 1 is higher priority
         than 2, which is higher than 3.
         - only BSS 3 transmits full bandwidth traffic: BSS 3 gets full bandwidth
         - BSS 2 starts transmitting at 2 Mb/s: BSS 2 gets 2 Mb/s, BSS 3 gets
           full-2 Mb/s
         - BSS 2 increases to 4 Mb/s: BSS 3 gets full-4 Mb/s, BSS 2 gets 4 Mb/s
         - BSS 2 increases to full: BSS 3 gets 3 Mb/s, BSS 2 gets full-3 Mb/s
         - BSS 1 starts transmitting at 2 Mb/s: BSS 3 gets 3 mbps, BSS 2 gets
           full-5 Mb/s, BSS 1 gets 2 Mb/s
         - BSS 1 increases to full: BSS 3 gets 3 Mb/s, BSS 2 gets 3 Mb/s, BSS 1
           gets full-6 Mb/s
           NOTE: NOT IMPLEMENTED"
    DEFVAL { 0 }
    ::= { tchRgDot11BssEntry 9 }

tchRgDot11BssDsBwPriority OBJECT-TYPE
    SYNTAX INTEGER (1..4)
    MAX-ACCESS  read-write
    STATUS      current
    DESCRIPTION
        "Sets the priority for non-reserved bandwidth. 1 is the highest priority.
         If BSSs use the same priority, they get bandwidth based on contention.
         NOTE: NOT IMPLEMENTED"
    DEFVAL { 4 }
    ::= { tchRgDot11BssEntry 10 }

tchRgDot11BssMaxNumSta OBJECT-TYPE
    SYNTAX INTEGER (1..128)
    MAX-ACCESS read-write
    STATUS current
    DESCRIPTION
        "This object defines the maximum number of STAs that can connect to
         this SSID. Note that the maximum number of STA accross all SSIDs in
         the AP is 128.
         Default value is 128 for all SSIDs.
         The value for primary BSS is stored in non-vol."
    ::= { tchRgDot11BssEntry 11 }

tchRgDot11BssCountStaAsCpe OBJECT-TYPE
    SYNTAX TruthValue
    MAX-ACCESS read-only
    STATUS current
    DESCRIPTION
        "STAs in Max-Count of CPEs (Max number of CPE in CM config file),
         default per eDOCSIS spec.
         This setting is used to control counting STAs in Max-Count of CPEs.
         false: Do not count STAs as a CPE
         true: Count STAs as a CPE
         This object applies when the BSS is in bridge mode. In router mode
         the STAs are behind the NAT and do not count towards max-CPE anyway.
         Note: applies only to secondary BSSs."
    DEFVAL { true }
    ::= { tchRgDot11BssEntry 12 }

tchRgDot11BssUserStatus OBJECT-TYPE
    SYNTAX INTEGER {
        enable(1),
        disable(2)
        }
    MAX-ACCESS  read-only
    STATUS      current
    DESCRIPTION
        "Provides the BSS Id Web UI or Wireless ON/OFF (if exist) status that
                  is set by the user. If the user can press the Wireless ON/OFF (if
                  exist) button and its status can be seen in BSS ID Web UI. If user
                  changes access point status in Web UI, it will reflect the status of
                  Wireless ON/OFF LED."
    ::= { tchRgDot11BssEntry 13 }

tchRgDot11BssHotSpot OBJECT-TYPE
    SYNTAX TruthValue
    MAX-ACCESS read-write
    STATUS current
    DESCRIPTION
        "Determines/Sets whether this BSS is a HotSpot BSS.  This allows the MSO to
                 specify which BSS is configured for Hotspot Operation.
         Note: applies only to Guest BSSs (non primary)."
    DEFVAL { false }
    ::= { tchRgDot11BssEntry 14 }


tchRgDot11BssApIsolation OBJECT-TYPE
    SYNTAX INTEGER {
        disable(0),
        enable(1)
        }
    MAX-ACCESS  read-write
    STATUS      current
    DESCRIPTION
        "This MIB is only available in D3.0 products.
        AP Isolation (Access Point Isolation) allows you to isloate traffic between CPEs on
        the same Wifi SSID. This allows a measure of security to prevent hackers from accessing other CPEs in
        a public Wifi environment.
        Ex. When this MIB is enabled you can not ping between CPEs connected to the same SSID.
        AP Isolation is settable per SSID in either VLAN or non VLAN modes.
        This MIB is written to non-vol and set to disable(0) after a factory reset.
        disable(0)- No AP Isolation
        enable(1)- Enable AP Isolation feature."
    DEFVAL { 0 }
    ::= { tchRgDot11BssEntry 15 }

tchRgDot11BssSecSsidTrafficPriority OBJECT-TYPE
    SYNTAX INTEGER {
        disable(0),
        acBk(1)
        }
    MAX-ACCESS  read-only
    STATUS      current
    DESCRIPTION
        "This MIB is only available in D3.0 products and applicable for secondary SSID in hotspot
        environment. When disabled, all the traffic to the secondary SSID in question would have same WMM QoS
        parameters as the primary SSID. When set to ac_bk(1), the secondary SSID traffic would be classified as
        AC_BK resulting in better DS prioritization for primary SSID traffic"

    DEFVAL { 0 }
    ::= { tchRgDot11BssEntry 16 }

tchRgDot11BssRejectPriSsidSta OBJECT-TYPE
    SYNTAX TruthValue
    MAX-ACCESS  read-only
    STATUS      current
    DESCRIPTION
        "This MIB is only available in D3.0 products and applicable for secondary SSID in hotspot
        environment. By default, a private SSID STA can associate to hotspot SSID. This MIB can be used
        to reject private SSID STAs to associate with hotspot SSID if and only if STA has associated with private
        SSID once before."

    DEFVAL { false }
    ::= { tchRgDot11BssEntry 17 }
    
tchRgDot11BssRejectPriSsidStaCount OBJECT-TYPE
      SYNTAX INTEGER {
        disable(0),
        enable(1)
        }
      MAX-ACCESS read-write
      STATUS      current
    DESCRIPTION
        "This MIB is only available in D3.0 products and applicable for secondary SSID in hotspot
        environment.This MIB should be used in conjunction with tchRgDot11BssRejectPriSsidSta. When both enable it is
        possible for the STA to connect for one time to the secondary SSID instead of zero times when only 
        tchRgDot11BssRejectPriSsidSta is enable"

    DEFVAL { 0 }
    ::= { tchRgDot11BssEntry 18 }
	
tchRgDot11BssFactoryResetSSID  OBJECT-TYPE
      SYNTAX TruthValue
      MAX-ACCESS read-write
      STATUS      current
    DESCRIPTION
        "This MIB is used to factory reset particular SSID & AccessPoint. Eg: If tchRgDot11BssFactoryResetSSID.10001 is set to true, then all the settings in Device.WiFi.SSID.1 and Device.WiFi.AccessPoint.1 will be set to defaults."

    DEFVAL { false }
    ::= { tchRgDot11BssEntry 19 }
	
tchRgDot11BssPMFcontrol OBJECT-TYPE
      SYNTAX INTEGER {
        disabled(0),
        optional(1),
	required(2)
        }
      MAX-ACCESS read-write
      STATUS      current
    DESCRIPTION
        "This MIB is used to control the protected management frame (802.11w).
		disabled - No PMF protection
		optional - legacy client will connect and PMF for 802.11w clients
		required - only 802.11w client alone connect
		After factory reset optional(1) will be set"

    DEFVAL { 1 }
    ::= { tchRgDot11BssEntry 20 }

tchRgDot11BssTostagging OBJECT-TYPE
    SYNTAX INTEGER (1..63)
    MAX-ACCESS read-write
    STATUS current
    DESCRIPTION
        "This object defines the tos tagging  to
         this SSID for hotspot purposes. 
         Note that the maximum tos value is 63.
         Default value is 63 for all SSIDs.
         The value for primary BSS is stored in non-vol."

    DEFVAL { 63 }    
    ::= { tchRgDot11BssEntry 21 }


-- RESTRICT ACCESS WITH MAC TABLE

tchRgDot11AccessMacTable  OBJECT-TYPE
    SYNTAX      SEQUENCE OF TchRgDot11AccessMacEntry
    MAX-ACCESS  not-accessible
    STATUS      current
    DESCRIPTION
        "A table of MAC addresses which represents stations that will be allowed
         to connect to the device if tchRgDot11AccessMode is set to
         restrictToList(1)."
    ::= { tchRgDot11Bss 2 }

tchRgDot11AccessMacEntry OBJECT-TYPE
    SYNTAX      TchRgDot11AccessMacEntry
    MAX-ACCESS  not-accessible
    STATUS      current
    DESCRIPTION
        "A row in the table that specifies a single station MAC address."
    INDEX   { ifIndex, tchRgDot11AccessMacIndex }
    ::= { tchRgDot11AccessMacTable 1 }

TchRgDot11AccessMacEntry ::=
    SEQUENCE    {
                tchRgDot11AccessMacIndex       INTEGER,
                tchRgDot11AccessMacStation     MacAddress,
                tchRgDot11BssAccessStatus      RowStatus,
                tchRgDot11AccessMacDeviceName  SnmpAdminString
    }

tchRgDot11AccessMacIndex OBJECT-TYPE
    SYNTAX      INTEGER (1..32)
    MAX-ACCESS  not-accessible
    STATUS      current
    DESCRIPTION
        "Indicates the instance of this table row."
    ::= { tchRgDot11AccessMacEntry 1 }

tchRgDot11AccessMacStation OBJECT-TYPE
    SYNTAX      MacAddress
    MAX-ACCESS  read-create
    STATUS      current
    DESCRIPTION
        "A MAC address of a station which will be allowed to connect to the
         device if tchRgDot11AccessMode is set to restrictToList(1)."
    ::= { tchRgDot11AccessMacEntry 2 }

tchRgDot11BssAccessStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         dot11BssAccessStatus column is 'notReady'.

         In particular, a newly created row cannot be made active until the
         corresponding instance of dot11BssAccessStation has been set.

         Only rows with a status of active(1) will be applied."
    ::= { tchRgDot11AccessMacEntry 3 }

tchRgDot11AccessMacDeviceName OBJECT-TYPE
    SYNTAX      SnmpAdminString 
    MAX-ACCESS  read-create
    STATUS      current
    DESCRIPTION
        "This is the device name given to the Mac Address of a station(tchRgDot11AccessMacStation)."
    ::= { tchRgDot11AccessMacEntry 4 }

-- PRIMARY BSS SPECIFIC

tchRgDot11BssPrimary OBJECT IDENTIFIER ::= { tchRgDot11Bss 3 }

tchRgDot11BssPrimarySsidType OBJECT-TYPE
    SYNTAX INTEGER {
        mac6char(1),
        mac6char-prefix(2),
        mac4char-prefix(3),
        prefix-force(4),
        prefix-default(5)
        }
    MAX-ACCESS  read-write
    STATUS      current
    DESCRIPTION
        "This object specifies the type of SSID used.
         mac6char(1): If tchRgDot11BssSsid.32 is empty, the SSID is the last
                      3 bytes of DOCSIS MAC address, displayed as 6 lowercase
                      hex characters.
                      If tchRgDot11BssSsid.32 is not empty, SSID is the value from
                      tchRgDot11BssSsid.32 (set by SNMP or the user).
         mac6char-prefix(2): the same as mac6char(2) with the prefix addition
                             defined in tchRgDot11BssPrimarySsidPrefix.
                             If  tchRgDot11BssSsid.32 is not empty, this prefix
                             does not show.
         mac4char-prefix(3): the same as mac6char-prefix(2) but 4 MAC characters
                             instead of 6.
         prefix-force(4): The prefix is always included, even if tchRgDot11BssSsid.32
                          is empty.
		 prefix-default(5): The prefix defined in tchRgDot11BssPrimarySsidPrefix replace the current default SSID prefix
         Note: stored in non-vol. mac6char(1) after factory reset"
    ::= { tchRgDot11BssPrimary 1 }

tchRgDot11BssPrimarySsidPrefix OBJECT-TYPE
    SYNTAX SnmpAdminString (SIZE(1..16))
    MAX-ACCESS  read-write
    STATUS      current
    DESCRIPTION
        "The prefix for primary SSID, if tchRgDot11BssSsid.32 is empty
         and tchRgDot11BssPrimarySsidType is set to mac6char-prefix(2).
         Stored in non-vol. Empty after factory reset."
    ::= { tchRgDot11BssPrimary 2 }

tchRgDot11BssPrimarySsidSuffix OBJECT-TYPE
    SYNTAX INTEGER {
        disable(0),
        suffix2-4(1),
        suffix5(2),
        suffixboth(3)
        }
    MAX-ACCESS read-write
    STATUS     current
    DESCRIPTION
        "The suffix for primary SSID. Default no suffix is added. 
        suffix2-4(1): -2.4G will be added as suffix for the 2.4Ghz band
        suffix5(2): -5G will be added as suffix for the 5Ghz band
        suffixboth(3): Both -2.4G and -5G will be added as suffix to the corresponding frequency band.
         "  
    DEFVAL { 0 }
    ::= { tchRgDot11BssPrimary 3 }

-- RESTRICT ACCESS WITH HOTSPOT MAC TABLE

tchRgDot11AccessHotspotMacTable  OBJECT-TYPE
    SYNTAX      SEQUENCE OF TchRgDot11AccessHotspotMacEntry
    MAX-ACCESS  not-accessible
    STATUS      current
    DESCRIPTION
        "A table of MAC addresses which represents stations that will be allowed
         to connect to the device if tchRgDot11AccessMode is set to
         restrictToList(1)."
    ::= { tchRgDot11Bss 4 }

tchRgDot11AccessHotspotMacEntry OBJECT-TYPE
    SYNTAX      TchRgDot11AccessHotspotMacEntry
    MAX-ACCESS  not-accessible
    STATUS      current
    DESCRIPTION
        "A row in the table that specifies a single station MAC address."
    INDEX   { ifIndex, tchRgDot11AccessHotspotMacIndex }
    ::= { tchRgDot11AccessHotspotMacTable 1 }

TchRgDot11AccessHotspotMacEntry ::=
    SEQUENCE    {
                tchRgDot11AccessHotspotMacIndex       INTEGER,
                tchRgDot11AccessHotspotMacStation     MacAddress,
                tchRgDot11BssAccessHotspotStatus      RowStatus
    }

tchRgDot11AccessHotspotMacIndex OBJECT-TYPE
    SYNTAX      INTEGER (1..32)
    MAX-ACCESS  not-accessible
    STATUS      current
    DESCRIPTION
        "Indicates the instance of this table row."
    ::= { tchRgDot11AccessHotspotMacEntry 1 }

tchRgDot11AccessHotspotMacStation OBJECT-TYPE
    SYNTAX      MacAddress
    MAX-ACCESS  read-create
    STATUS      current
    DESCRIPTION
        "A MAC address of a station which will be allowed to connect to the
         device if tchRgDot11AccessMode is set to restrictToList(1)."
    ::= { tchRgDot11AccessHotspotMacEntry 2 }

tchRgDot11BssAccessHotspotStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         dot11BssAccessStatus column is 'notReady'.

         In particular, a newly created row cannot be made active until the
         corresponding instance of dot11BssAccessStation has been set.

         Only rows with a status of active(1) will be applied."
    ::= { tchRgDot11AccessHotspotMacEntry 3 }


-- MAC ANONYMOUS ADDRESS

tchRgDot11AccessMacAnonymousTable  OBJECT-TYPE
    SYNTAX      SEQUENCE OF TchRgDot11AccessMacAnonymousEntry
    MAX-ACCESS  not-accessible
    STATUS      current
    DESCRIPTION
        "A table of MAC addresses which represents stations that will be allowed
         to connect to the device if tchRgDot11AccessMode is set to
         restrictToList(1)."
    ::= { tchRgDot11Bss 5 }

tchRgDot11AccessMacAnonymousEntry OBJECT-TYPE
    SYNTAX      TchRgDot11AccessMacAnonymousEntry
    MAX-ACCESS  not-accessible
    STATUS      current
    DESCRIPTION
        "A row in the table that specifies a single station MAC address."
    INDEX   { ifIndex, tchRgDot11AccessMacAnonymousIndex }
    ::= { tchRgDot11AccessMacAnonymousTable 1 }

TchRgDot11AccessMacAnonymousEntry ::=
    SEQUENCE    {
                tchRgDot11AccessMacAnonymousIndex       INTEGER,
                tchRgDot11AccessMacAnonymousStation     MacAddress
    }

tchRgDot11AccessMacAnonymousIndex OBJECT-TYPE
    SYNTAX      INTEGER (1..32)
    MAX-ACCESS  not-accessible
    STATUS      current
    DESCRIPTION
        "Indicates the instance of this table row."
    ::= { tchRgDot11AccessMacAnonymousEntry 1 }

tchRgDot11AccessMacAnonymousStation OBJECT-TYPE
    SYNTAX      MacAddress
    MAX-ACCESS  read-only
    STATUS      current
    DESCRIPTION
        "A MAC address in Anonymous format
		 [all but the first three bytes (OUI) MUST be set to zero]
		 of a station which will be allowed to connect to the
         device if tchRgDot11AccessAnonymMode is set to restrictToList(1)."
    ::= { tchRgDot11AccessMacAnonymousEntry 2 }


    
-- ******************
-- PRIVACY PARAMETERS
-- ******************

-- tchRgDot11MgmtPrivacy contains objects from the 'Privacy' web page

tchRgDot11Privacy OBJECT IDENTIFIER ::= { tchRgDot11 3 }


-- WPA

tchRgDot11WpaTable  OBJECT-TYPE
    SYNTAX      SEQUENCE OF TchRgDot11WpaEntry
    MAX-ACCESS  not-accessible
    STATUS      current
    DESCRIPTION
        "WPA table"
    ::= { tchRgDot11Privacy 1 }

tchRgDot11WpaEntry OBJECT-TYPE
    SYNTAX      TchRgDot11WpaEntry
    MAX-ACCESS  not-accessible
    STATUS      current
    DESCRIPTION
        "A row in the table which represents WPA parameters for BSS."
    INDEX   { ifIndex }
    ::= { tchRgDot11WpaTable 1 }

TchRgDot11WpaEntry ::=
    SEQUENCE    {
        tchRgDot11WpaAlgorithm          INTEGER,
        tchRgDot11WpaPreSharedKey       OCTET STRING,
        tchRgDot11WpaGroupRekeyInterval INTEGER
    }

tchRgDot11WpaAlgorithm OBJECT-TYPE
    SYNTAX INTEGER {
        tkip(0),
        aes(1),
        tkipPlusAes(2)
        }
    MAX-ACCESS  read-write
    STATUS      current
    DESCRIPTION
        "The value of tkip(0) is not allowed when security is WPA2.
         The value for primary BSS is stored in non-vol and tkipPlusAes(2)
         after factory reset.
         The default value for other BSSs is tkip."
    ::= { tchRgDot11WpaEntry 1 }

tchRgDot11WpaPreSharedKey OBJECT-TYPE
    SYNTAX      OCTET STRING (SIZE(8..64))
    MAX-ACCESS  read-write
    STATUS      current
    DESCRIPTION
        "Sets the WPA Pre-Shared Key (PSK).  This value MUST be either a
         64-digit hexadecimal number, OR a 8 to 63 character ASCII string.
         The value for primary BSS is stored in non-vol and is the serial
         number of the device after factory reset.
         The default value for other BSSs is 8 0's.
         This object return an empty string when read."
    ::= { tchRgDot11WpaEntry 2 }

tchRgDot11WpaGroupRekeyInterval OBJECT-TYPE
    SYNTAX      INTEGER
    UNITS       "seconds"
    MAX-ACCESS  read-write
    STATUS      current
    DESCRIPTION
        "Sets the WPA Group Rekey Interval in seconds. Set to zero to disable
         periodic rekeying.
         The value for primary BSS is stored in non-vol and is 3600 after
         factory reset.
         The default value for other BSSs is 3600."
    ::= { tchRgDot11WpaEntry 3 }


-- RADIUS

tchRgDot11RadiusTable  OBJECT-TYPE
    SYNTAX      SEQUENCE OF TchRgDot11RadiusEntry
    MAX-ACCESS  not-accessible
    STATUS      current
    DESCRIPTION
        "WPA table"
    ::= { tchRgDot11Privacy 2 }

tchRgDot11RadiusEntry OBJECT-TYPE
    SYNTAX      TchRgDot11RadiusEntry
    MAX-ACCESS  not-accessible
    STATUS      current
    DESCRIPTION
        "A row in the table which represents WPA parameters for BSS."
    INDEX   { ifIndex }
    ::= { tchRgDot11RadiusTable 1 }

TchRgDot11RadiusEntry ::=
    SEQUENCE    {
        tchRgDot11RadiusAddressType    InetAddressType,
        tchRgDot11RadiusAddress        InetAddress,
        tchRgDot11RadiusPort           InetPortNumber,
        tchRgDot11RadiusKey            DisplayString,
        tchRgDot11RadiusReAuthInterval INTEGER
    }


tchRgDot11RadiusAddressType OBJECT-TYPE
    SYNTAX      InetAddressType
    MAX-ACCESS  read-write
    STATUS      current
    DESCRIPTION
            "Type of RADIUS server IP address."
    DEFVAL { ipv4 }
    ::= { tchRgDot11RadiusEntry 1 }


tchRgDot11RadiusAddress OBJECT-TYPE
    SYNTAX      InetAddress
    MAX-ACCESS  read-write
    STATUS      current
    DESCRIPTION
        "Sets RADIUS server IP address.
         The value for primary BSS is stored in non-vol and is 0.0.0.0
         after factory reset.
         The default value for other BSSs is 0.0.0.0."
    ::= { tchRgDot11RadiusEntry 2 }

tchRgDot11RadiusPort OBJECT-TYPE
    SYNTAX      InetPortNumber
    MAX-ACCESS  read-write
    STATUS      current
    DESCRIPTION
        "Sets the UDP port used to communicate with the RADIUS server.
         The value for primary BSS is stored in non-vol and is 1645
         after factory reset.
         The default value for other BSSs is 1645."
    ::= { tchRgDot11RadiusEntry 3 }

tchRgDot11RadiusKey OBJECT-TYPE
    SYNTAX      DisplayString
    MAX-ACCESS  read-write
    STATUS      current
    DESCRIPTION
        "Sets or displays the RADIUS key.
         The value for primary BSS is stored in non-vol and is null
         after factory reset.
         The default value for other BSSs is null.
         This object return an empty string when read."
    ::= { tchRgDot11RadiusEntry 4 }

tchRgDot11RadiusReAuthInterval OBJECT-TYPE
    SYNTAX      INTEGER
    UNITS       "seconds"
    MAX-ACCESS  read-write
    STATUS      current
    DESCRIPTION
        "Sets the RADIUS Rekey Interval in seconds.
         Set to zero to disable periodic rekeying.
         The value for primary BSS is stored in non-vol and is 3600
         after factory reset.
         The default value for other BSSs is 3600."
    ::= { tchRgDot11RadiusEntry 5 }


-- WEP

tchRgDot11WepTable  OBJECT-TYPE
    SYNTAX      SEQUENCE OF TchRgDot11WepEntry
    MAX-ACCESS  not-accessible
    STATUS      current
    DESCRIPTION
        "WEP table"
    ::= { tchRgDot11Privacy 3 }

tchRgDot11WepEntry OBJECT-TYPE
    SYNTAX      TchRgDot11WepEntry
    MAX-ACCESS  not-accessible
    STATUS      current
    DESCRIPTION
        "A row in the table which represents WPA parameters for BSS."
    INDEX   { ifIndex }
    ::= { tchRgDot11WepTable 1 }

TchRgDot11WepEntry ::=
    SEQUENCE {
        tchRgDot11WepDefaultKey      INTEGER,
        tchRgDot11WepEncryptionMode  INTEGER,
        tchRgDot11WepPassPhrase      DisplayString
    }

tchRgDot11WepDefaultKey OBJECT-TYPE
    SYNTAX      INTEGER (1..4)
    MAX-ACCESS  read-write
    STATUS      current
    DESCRIPTION
        "Controls and reflects the default key which will be used when 64 or
         128 bit encryption is enabled.  Indicates the entry from the
         tchRgDot1164BitKeyTable if tchRgDot11EncryptionMode is set to wep64(1), or
         the entry from the tchRgDot11128BitKeyTable if tchRgDot11EncryptionMode is set
         to wep128(2).
         The value for primary BSS is stored in non-vol and is 1 after factory reset.
         The default value for other BSSs is 1."
    ::= { tchRgDot11WepEntry 1 }

tchRgDot11WepEncryptionMode OBJECT-TYPE
    SYNTAX INTEGER {
        wep64(0),
        wep128(1)
        }
    MAX-ACCESS  read-write
    STATUS      current
    DESCRIPTION
         "The value for primary BSS is stored in non-vol and is wep128(1)
          after factory reset.
          The default value for other BSSs is wep128."
    ::= { tchRgDot11WepEntry 2 }

tchRgDot11WepPassPhrase OBJECT-TYPE
    SYNTAX      DisplayString (SIZE(0..32))
    MAX-ACCESS  read-write
    STATUS      current
    DESCRIPTION
        "Controls and reflects the WEP pass phrase.
         The value for primary BSS is stored in non-vol and is null
         after factory reset.
         The default value for other BSSs is null.
         This object return an empty string when read."
    ::= { tchRgDot11WepEntry 3 }



-- WEP 64-bit keys:

tchRgDot11Wep64BitKeyTable  OBJECT-TYPE
    SYNTAX      SEQUENCE OF TchRgDot11Wep64BitKeyEntry
    MAX-ACCESS  not-accessible
    STATUS      current
    DESCRIPTION
        "A table of 40 bit key values used when tchRgDot11WepEncryptionMode
         is set to wep64(0)."
    ::= { tchRgDot11Privacy 4 }

tchRgDot11Wep64BitKeyEntry OBJECT-TYPE
    SYNTAX      TchRgDot11Wep64BitKeyEntry
    MAX-ACCESS  not-accessible
    STATUS      current
    DESCRIPTION
        "A row in the table which represents a single 64 bit key."
    INDEX   { ifIndex, tchRgDot11Wep64BitKeyIndex }
    ::= { tchRgDot11Wep64BitKeyTable 1 }

TchRgDot11Wep64BitKeyEntry ::=
    SEQUENCE    {
                tchRgDot11Wep64BitKeyIndex       Integer32,
                tchRgDot11Wep64BitKeyValue       OCTET STRING
    }

tchRgDot11Wep64BitKeyIndex OBJECT-TYPE
    SYNTAX      Integer32 (1..4)
    MAX-ACCESS  not-accessible
    STATUS      current
    DESCRIPTION
        "Identifies the instance of this table row."
    ::= { tchRgDot11Wep64BitKeyEntry 1 }

tchRgDot11Wep64BitKeyValue OBJECT-TYPE
    SYNTAX      OCTET STRING (SIZE(5))
    MAX-ACCESS  read-write
    STATUS      current
    DESCRIPTION
        "A 40 bit key to be used when tchRgDot11WepEncryptionMode is set to wep64(1).
         The value for primary BSS is stored in non-vol and is all 1's after factory
         reset.
         The default value for other BSSs is all 0's.
         This object return an empty string when read."
    ::= { tchRgDot11Wep64BitKeyEntry 2 }

-- WEP 128-bit keys:

tchRgDot11Wep128BitKeyTable  OBJECT-TYPE
    SYNTAX      SEQUENCE OF TchRgDot11Wep128BitKeyEntry
    MAX-ACCESS  not-accessible
    STATUS      current
    DESCRIPTION
        "A table of 104 bit key values used when tchRgDot11WepEncryptionMode
         is set to wep128(1)."
    ::= { tchRgDot11Privacy 5 }

tchRgDot11Wep128BitKeyEntry OBJECT-TYPE
    SYNTAX      TchRgDot11Wep128BitKeyEntry
    MAX-ACCESS  not-accessible
    STATUS      current
    DESCRIPTION
        "A row in the table which represents a single 128 bit key."
    INDEX   { ifIndex, tchRgDot11Wep128BitKeyIndex }
    ::= { tchRgDot11Wep128BitKeyTable 1 }

TchRgDot11Wep128BitKeyEntry ::=
    SEQUENCE    {
                tchRgDot11Wep128BitKeyIndex       Integer32,
                tchRgDot11Wep128BitKeyValue       OCTET STRING
    }

tchRgDot11Wep128BitKeyIndex OBJECT-TYPE
    SYNTAX      Integer32 (1..4)
    MAX-ACCESS  not-accessible
    STATUS      current
    DESCRIPTION
        "Identifies the instance of this table row."
    ::= { tchRgDot11Wep128BitKeyEntry 1 }

tchRgDot11Wep128BitKeyValue OBJECT-TYPE
    SYNTAX      OCTET STRING (SIZE(13))
    MAX-ACCESS  read-write
    STATUS      current
    DESCRIPTION
        "A 104 bit key to be used when tchRgDot11WepEncryptionMode is set to wep128(2).
         The value for primary BSS is stored in non-vol and is all 1's.
         The default value for other BSSs is all 0's.
         This object return an empty string when read."
    ::= { tchRgDot11Wep128BitKeyEntry 2 }


tchRgDot11PrivacyWps OBJECT IDENTIFIER ::= { tchRgDot11Privacy 6 }

tchRgDot11PrivacyWpsPushButtonTime OBJECT-TYPE
    SYNTAX      INTEGER (0..10)
    UNITS       "seconds"
    MAX-ACCESS  read-write
    STATUS      current
    DESCRIPTION
        "Specifies how long to press WPS button to start the WPS
         procedure. 0 means disable WPS.
         Stored in non-vol, 1 after factory reset."
    ::= { tchRgDot11PrivacyWps 1 }


-- ASSOCIATED CLIENTS TREE

tchRgDot11Client OBJECT IDENTIFIER ::=  { tchRgDot11 4 }

tchRgDot11ClientBase OBJECT IDENTIFIER ::=  { tchRgDot11Client 1 }

tchRgDot11ClientTable  OBJECT-TYPE
    SYNTAX      SEQUENCE OF TchRgDot11ClientEntry
    MAX-ACCESS  not-accessible
    STATUS      current
    DESCRIPTION
        "A table of wireless clients that are associated with the BSS."
    ::= { tchRgDot11Client 2 }

tchRgDot11ClientCounterTable  OBJECT-TYPE
    SYNTAX      SEQUENCE OF TchRgDot11ClientCounterEntry
    MAX-ACCESS  not-accessible
    STATUS      current
    DESCRIPTION
        "A table of numbers of clients for each SSID."
    ::= { tchRgDot11ClientBase 1 }

tchRgDot11ClientCounterEntry OBJECT-TYPE
    SYNTAX      TchRgDot11ClientCounterEntry
    MAX-ACCESS  not-accessible
    STATUS      current
    DESCRIPTION
        "A row in the table that shows number of Clients."
    INDEX   { ifIndex, tchRgDot11ClientCounterIndex }
    ::= { tchRgDot11ClientCounterTable 1 }

TchRgDot11ClientCounterEntry ::=
    SEQUENCE    {
        tchRgDot11ClientCounterIndex INTEGER,        
        tchRgDot11ClientCounter      INTEGER
    }

tchRgDot11ClientCounterIndex OBJECT-TYPE
    SYNTAX	INTEGER (1..128)
    MAX-ACCESS  not-accessible
    STATUS current
    DESCRIPTION
         "The index"
    ::= { tchRgDot11ClientCounterEntry 1 }

tchRgDot11ClientCounter OBJECT-TYPE
    SYNTAX      INTEGER
    MAX-ACCESS  read-only
    STATUS      current
    DESCRIPTION
        "Number Of Clients of a SSID."
    ::= { tchRgDot11ClientCounterEntry 2 }

tchRgDot11ClientEntry OBJECT-TYPE
    SYNTAX      TchRgDot11ClientEntry
    MAX-ACCESS  not-accessible
    STATUS      current
    DESCRIPTION
        "A row in the table that specifies a single station MAC address."
    INDEX   { ifIndex, tchRgDot11ClientIndex }
    ::= { tchRgDot11ClientTable 1 }

TchRgDot11ClientEntry ::=
    SEQUENCE    {
                tchRgDot11ClientIndex       Integer32,
                tchRgDot11ClientStation     MacAddress,
                tchRgDot11ClientConnectMode INTEGER
    }

tchRgDot11ClientIndex OBJECT-TYPE
    SYNTAX      Integer32 (0..127)
    MAX-ACCESS  not-accessible
    STATUS      current
    DESCRIPTION
        "Indicates the instance of this table row."
    ::= { tchRgDot11ClientEntry 1 }

tchRgDot11ClientStation OBJECT-TYPE
    SYNTAX      MacAddress
    MAX-ACCESS  read-only
    STATUS      current
    DESCRIPTION
        "A MAC address of a client associated with the BSS."
    ::= { tchRgDot11ClientEntry 2 }

tchRgDot11ClientConnectMode OBJECT-TYPE
    SYNTAX INTEGER {
        disable(0),
        a(1),
        g(2),
        n(3)
        }
    MAX-ACCESS read-only
    STATUS     current
    DESCRIPTION
        "This MIB will query WiFi client info. If no info found, return disable(0). When information is found, return connect mode a(1),g(2),or n(3)."  
    DEFVAL { 0 }
    ::= { tchRgDot11ClientEntry 3 }


--  802.11n settings

tchRgDot11n OBJECT IDENTIFIER ::= { tchRgDot11 5 }

tchRgdot11nMode OBJECT-TYPE
    SYNTAX INTEGER {
        auto(1),
        off(2),
        n-only(3),
        b-mode(16),
        g-mode(32),
        bg-mode(48),
        a-mode(64),
        n-only-bitmask(128),    -- to differentiate from n-only(3)
        gn-mode(160),
        bgn-mode(176),
        an-mode(192),
        ac-only(256),
        nac-only(384),
        anac-mode(448)
        }

    MAX-ACCESS  read-write
    STATUS      current
    DESCRIPTION
        "Determines which 802.11 mode the radio will run in.
         This object must be set by either the legacy or bitmask method.

         In legacy method,
         auto(1)  : supports all the 802.11 modes available in the radio.
         off(2)   : supports the legacy mode only (11b/g in 2.4GHz and 11a in 5GHz).
         n-only(3): accepts 11n-capable clients only but supports all the modes available in the radio.

         In bitmask method,
         b-mode(16)    : supports 11b mode in 2.4GHz.
         g-mode(32)    : supports 11g mode in 2.4GHz.
         bg-mode(48)   : supports 11b/g mode in 2.4GHz (16+32).
         a-mode(64)    : supports 11a mode in 5GHz.
         n-only-bitmask(128)   : accepts 11n-capable clients only but supports both legacy and 11n modes in 2.4GHz or 5GHz.
         gn-mode(160)  : supports 11g/n mode in 2.4GHz (32+128).
         bgn-mode(176) : supports all 11b/g/n modes in 2.4GHz (16+32+128).
         an-mode(192)  : supports 11a/n modes in 5GHz (64+128).
         ac-only(256)  : accepts 11ac-capable clients only but supports 11a/n/ac modes in 5GHz.
         nac-only(384) : accepts 11n-capable clients only but supports 11a/n/ac modes in 5GHz (128+256).
         anac-mode(448): supports all 11a/n/ac modes in 5GHz (64+128+256).

         Note: Some options may not be available depending on the radio model.
         Note: The change of this object value will also affect other MIB selections, including tchRgdot11nExtBandWidth.
         This object is stored in non-vol and defaults to auto(1) after factory reset."
    ::= { tchRgDot11n 1 }

tchRgdot11nPhyRate OBJECT-TYPE
    SYNTAX INTEGER {
        auto(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the N Phy transmission rate for the AP to a particular speed.  Each pair of rates
         corresponds to a 20 MHz or 40 MHz channel configuration.
         This object is stored in non-vol and defaults to auto(0) after factory reset."
    DEFVAL { auto }
    ::= { tchRgDot11n 2 }


tchRgdot11nBand OBJECT-TYPE
    SYNTAX INTEGER {
        band-2-4G(1),
        band-5G(2)
        }
    MAX-ACCESS  read-write
    STATUS      current
    DESCRIPTION
        "Determines which Band that we will be operating in. Either the 2.4G or the 5G Hz.
         Note: This is for N cards only.
         This object is stored in non-vol and defaults to band-2-4G(1) after factory reset."
    ::= { tchRgDot11n 3 }

tchRgdot11nBandWidth OBJECT-TYPE
    SYNTAX INTEGER {
        width-20MHz(1),
        width-40MHz(2),
        width-80MHz(3)
        }
    MAX-ACCESS  read-write
    STATUS      current
    DESCRIPTION
        "Determines which Band Width that we will be operating in. Either the 20MHz or the 40MHz.
         Note: This is for N cards only, and this also affect other MIB selections such as tchRgdot11nSideBand.
         The 80 MHz channel width is only applicable for 802.11ac capable cards. If a user sets this to 80 MHz, SNMPset would fail for non-802.11ac cards
         This object is stored in non-vol and defaults to ? after factory reset."
    ::= { tchRgDot11n 4 }

tchRgdot11nSideBand OBJECT-TYPE
    SYNTAX INTEGER {
        upper(1),
        lower(2)
        }
    MAX-ACCESS  read-write
    STATUS      current
    DESCRIPTION
        "Determines which side Band the channel will operate in.
         Note: This is for N cards only, this mib is dependent of what tchRgdot11nBandWidth is selected and only
         applies when 40MHz is selected.
         This object is stored in non-vol and defaults to lower(2) after factory reset."
    ::= { tchRgDot11n 5 }

tchRgdot11nProtection OBJECT-TYPE
    SYNTAX INTEGER {
        auto(1),
        off(2)
        }
    MAX-ACCESS  read-write
    STATUS      current
    DESCRIPTION
        "Determines if protection will be turned on or off for N mode.
         Note: This is for N cards only.
         This object is stored in non-vol and defaults to auto(1) after factory reset."
    ::= { tchRgDot11n 6 }

tchRgdot11nObssCoex OBJECT-TYPE
        SYNTAX INTEGER {
                disable(0),
                enable(1)
                }
        MAX-ACCESS read-write
        STATUS     current
        DESCRIPTION
                "Allows MSO to control OBSS (Overlapping BSS) Coexistance parameter for 802.11n 40MHz channel width.
                 By default it is enabled and is stored in non-vol
                 Factory reset would clear it and would be enable(1) after factory reset.
                 When disabled, the 802.11n Wifi would stay in 40 MHz channel-width inspite of interference from other
                 wifi channels. While enabled, 802.11n would coexist with 802.11g channels using 20 MHz default channel-width
                 "
        ::= { tchRgDot11n 7 }

tchRgdot11nMulticastRate OBJECT-TYPE
    SYNTAX INTEGER {
        disable(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the dot11n Multicast Phy transmission rate.  Legacy mode forces the rate to be set
                 by dot11MulticastRate.
         This object is stored in non-vol and defaults to disable(0) after factory reset."
    DEFVAL { 0 }
    ::= { tchRgDot11n 8 }


----------------------------------------------------------------------
---  tchRgDot11ExtMgmt
---  Table to support Multiple Radios
---  Note: Indexes may be set to support specific hardware interfaces.
---  Index 32 MUST match tchRgDot11OperMode and vice versa
-----------------------------------------------------------------------

tchRgDot11ExtMgmt OBJECT IDENTIFIER ::= { tchRgDot11 6 }

tchRgDot11ExtMgmtTable  OBJECT-TYPE
    SYNTAX      SEQUENCE OF TchRgDot11ExtMgmtEntry
    MAX-ACCESS  not-accessible
    STATUS      current
    DESCRIPTION
        "Multiple Radio Configuration Table"
    ::= { tchRgDot11ExtMgmt 1 }

tchRgDot11ExtMgmtEntry OBJECT-TYPE
    SYNTAX      TchRgDot11ExtMgmtEntry
    MAX-ACCESS  not-accessible
    STATUS      current
    DESCRIPTION
        "A row in the table which represents parameters for a Radio.
                 Index 32 should be set for Radio 0 -- 2.4 GHz if populated.
                 Index 112 should be set for Radio 1"

    INDEX   { ifIndex }
    ::= { tchRgDot11ExtMgmtTable 1 }

TchRgDot11ExtMgmtEntry ::=
    SEQUENCE {
                tchRgDot11ExtOperMode                INTEGER,
                tchRgDot11ExtCurrentChannel          Unsigned32,
                tchRgDot11ExtBeaconInterval          Unsigned32,
                tchRgDot11ExtDTIMInterval            Unsigned32,
                tchRgDot11ExtFragThresh              Unsigned32,
                tchRgDot11ExtRTSThresh               Unsigned32,
                tchRgDot11ExtSRL                     Unsigned32,
                tchRgDot11ExtLRL                     Unsigned32,
                tchRgDot11ExtCtsProtectionEnable     TruthValue,
                tchRgDot11ExtRate                    INTEGER,
                tchRgDot11ExtOutputPower             INTEGER,
                tchRgDot11ExtCountry                 INTEGER,
                tchRgDot11ExtAntenna                 INTEGER,
                tchRgDot11ExtMbssUserControl         INTEGER,
                tchRgDot11ExtMbssUseNonvol           TruthValue,
                tchRgDot11ExtMbssAdminControl        INTEGER,
                tchRgDot11ExtActualChannel           INTEGER,
                tchRgDot11ExtOnOffPushButtonTime     INTEGER,
                tchRgDot11ExtWmm                     INTEGER,
                tchRgDot11ExtWmmNoAck                INTEGER,
                tchRgDot11ExtMulticastRate           INTEGER,
                tchRgDot11ExtWirelessButtonOperation INTEGER,
                tchRgDot11ExtWpsEnable               INTEGER,
                tchRgDot11ExtWpsPin                  Integer32,
                tchRgDot11ExtForceRescan             INTEGER,
				tchRgDot11ExtPowerSaveSupport		 INTEGER,
				tchRgDot11ExtWpsAPPinEnable			 INTEGER

        }

tchRgDot11ExtOperMode OBJECT-TYPE
    SYNTAX      INTEGER {
                notAvailable(0),
                off(1),
                remote(2),
                local(3)
    }
    MAX-ACCESS  read-write
    STATUS      current
    DESCRIPTION
        "Used to control the 802.11 operational mode. If set to
         notAvailable(0), then the wireless interface will be disabled, with
         the radio off, and no wireless settings web pages will be available to
         the user.
         If set to off(1) then the wireless interface will be disabled, but
         there may be a web page present which indicates that wireless service
         is available and that the MSO should be contacted to enable it.
         If set to remote(2), then the wireless interface will be enabled, but
         the configuration web pages are read-only so that the user may not
         change the settings.
         If set to local(3), then the wireless interface will be enabled, and
         the web pages will be read-write so that the user has full control over
         the settings.
         This parameter is stored in non-vol and set to local(3) after factory
         reset."
    ::= { tchRgDot11ExtMgmtEntry 1 }

tchRgDot11ExtCurrentChannel OBJECT-TYPE
    SYNTAX      Unsigned32 (0..216)
    MAX-ACCESS  read-write
    STATUS      current
    DESCRIPTION
        "Controls and reflects the current channel number.
         The value of 0 means auto channel selection.
         This parameter is stored in non-vol and is 0
         after factory reset.

         For 802.11b/g/n modes in 2.4 GHz, the available channels are 1-14.
         For 802.11a/n modes in 5 GHz, the available channels are 34-216.
         Channel selection is subjected to restrictions based on Wifi
         Country Code"
    ::= { tchRgDot11ExtMgmtEntry 3 }

tchRgDot11ExtBeaconInterval OBJECT-TYPE
    SYNTAX      Unsigned32  (1..65535)
    UNITS       "milliseconds"
    MAX-ACCESS  read-write
    STATUS      current
    DESCRIPTION
        "Controls and reflects the beacon interval for the device.
         This parameter is stored in non-vol."
    ::= { tchRgDot11ExtMgmtEntry 4 }

tchRgDot11ExtDTIMInterval OBJECT-TYPE
    SYNTAX      Unsigned32  (1..255)
    UNITS       "milliseconds"
    MAX-ACCESS  read-write
    STATUS      current
    DESCRIPTION
        "Controls and reflects the DTIM interval for the device.
         This parameter is stored in non-vol."
    ::= { tchRgDot11ExtMgmtEntry 5 }

-- Renamed from tchRgDot11FragmentationThreshold to avoid conflict w/ IEEE 802.11 MIB
tchRgDot11ExtFragThresh OBJECT-TYPE
    SYNTAX      Unsigned32  (256..2346)
    UNITS       "bytes"
    MAX-ACCESS  read-write
    STATUS      current
    DESCRIPTION
        "Controls and reflects the fragmentation threshold for the device.
         This parameter is stored in non-vol."
    ::= { tchRgDot11ExtMgmtEntry 6 }

-- Renamed from tchRgDot11RTSThreshold to avoid conflict w/ IEEE 802.11 MIB
tchRgDot11ExtRTSThresh OBJECT-TYPE
    SYNTAX      Unsigned32  (0..2347)
    MAX-ACCESS  read-write
    STATUS      current
    DESCRIPTION
        "Controls and reflects the RTS threshold for the device.
         This parameter is stored in non-vol."
    ::= { tchRgDot11ExtMgmtEntry 7 }


-- Renamed from tchRgDot11ShortRetryLimit to avoid conflict w/ IEEE 802.11 MIB
tchRgDot11ExtSRL OBJECT-TYPE
    SYNTAX      Unsigned32  (1..255)
    MAX-ACCESS  read-write
    STATUS      current
    DESCRIPTION
        "Controls and reflects the short retry limit for the device.
         This parameter is stored in non-vol."
    ::= { tchRgDot11ExtMgmtEntry 8 }

-- Renamed from tchRgDot11LongRetryLimit to avoid conflict w/ IEEE 802.11 MIB
tchRgDot11ExtLRL OBJECT-TYPE
    SYNTAX      Unsigned32  (1..255)
    MAX-ACCESS  read-write
    STATUS      current
    DESCRIPTION
        "Controls and reflects the long retry limit for the device.
         This parameter is stored in non-vol."
    ::= { tchRgDot11ExtMgmtEntry 9 }

tchRgDot11ExtCtsProtectionEnable OBJECT-TYPE
    SYNTAX      TruthValue
    MAX-ACCESS  read-write
    STATUS      current
    DESCRIPTION
        "Controls and reflects the state of CTS protection.
         If set to true(1), the AP will use RTS/CTS to improve 802.11
         performance in mixed 802.11 networks. Set to false(2) to
         maximize 802.11 throughput under most conditions.
         This parameter is stored in non-vol."
    ::= { tchRgDot11ExtMgmtEntry 10 }

tchRgDot11ExtRate OBJECT-TYPE
    SYNTAX      INTEGER {
                auto(0),
                mbits1(1),
                mbits2(2),
                mbits5-5(5),
                mbits6(6),
                mbits9(9),
                mbits11(11),
                mbits12(12),
                mbits18(18),
                mbits24(24),
                mbits36(36),
                mbits48(48),
                mbits54(54)
    }
    MAX-ACCESS  read-write
    STATUS      current
    DESCRIPTION
        "Forces the transmission rate for the AP to a particular speed.
         Note that the 802.11b rates, including mbits1(1), mbits2(2),
         mbits5-5(5), and mbits11(11), are not available in 5GHz.
         This parameter is stored in non-vol."
    ::= { tchRgDot11ExtMgmtEntry 11 }

tchRgDot11ExtOutputPower OBJECT-TYPE
    SYNTAX      INTEGER {
                percent25(25),
                percent50(50),
                percent75(75),
                percent100(100)
    }
    MAX-ACCESS  read-write
    STATUS      current
    DESCRIPTION
        "Sets the output power relative to the hardware's maximum capability.
         This parameter is stored in non-vol."
    ::= { tchRgDot11ExtMgmtEntry 12 }

tchRgDot11ExtCountry OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements.
         This parameter is stored in non-vol and is worldWide(0)
         (channels 1-11) after factory reset."
    ::= { tchRgDot11ExtMgmtEntry 13 }

tchRgDot11ExtAntenna OBJECT-TYPE
    SYNTAX  INTEGER {
        disableIntTx(0),
        enableIntTx(1)
        }
    MAX-ACCESS  read-write
    STATUS      current
    DESCRIPTION
        "This parameter is stored in non-vol and set to
         disableIntTx(0) after factory reset."
    ::= { tchRgDot11ExtMgmtEntry 14 }

tchRgDot11ExtMbssUserControl OBJECT-TYPE
    SYNTAX INTEGER (1..8|65536..16711680)
    MAX-ACCESS read-write
    STATUS current
    DESCRIPTION
        "Sets the number of user controlled Wifi networks via web pages.
         1: The user has control over the primary wireless network only.
            No guest network page is displayed.
         2: The user has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit Mask Control:
         Bit 16: -- User has control over Primary Wireless Network       :  65536
         Bit 17: -- User has control over Guest Network 1 (interface 33) : 131072
         Bit 18: -- User has control over Guest Network 2 (interface 34) : 262144
         Bit 19: -- User has control over Guest Network 3 (interface 35) : 524288
         Bit 20: -- User has control over Guest Network 4 (interface 36) :1048576
         Bit 21: -- User has control over Guest Network 5 (interface 37) :2097152
         Bit 22: -- User has control over Guest Network 6 (interface 38) :4194304
         Bit 23: -- User has control over Guest Network 7 (interface 39) :8388608

         This object value is stored in non-vol and set to 1
         after factory reset."
    ::= { tchRgDot11ExtMgmtEntry 15 }

tchRgDot11ExtMbssUseNonvol OBJECT-TYPE
    SYNTAX TruthValue
    MAX-ACCESS read-write
    STATUS current
    DESCRIPTION
        "Allows to save additional BSS parameters to non-vol if set to true.
         Primary BSS parameters are ALWAYS stored in non-vol.
         This object value is stored in non-vol and set to false
         after factory reset."
    ::= { tchRgDot11ExtMgmtEntry 16 }

tchRgDot11ExtMbssAdminControl OBJECT-TYPE
    SYNTAX INTEGER (1..8|65536..16711680)
    MAX-ACCESS read-write
    STATUS current
    DESCRIPTION
        "Sets the number of admin controlled Wifi networks via web pages.
         1: The admin has control over the primary wireless network only.
            No guest network page is displayed.
         2: The admin has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit 16: -- Admin Has control over Primary Wireless Network       :  65536
         Bit 17: -- Admin Has control over Guest Network 1 (interface 33) : 131072
         Bit 18: -- Admin Has control over Guest Network 2 (interface 34) : 262144
         Bit 19: -- Admin Has control over Guest Network 3 (interface 35) : 524288
         Bit 20: -- Admin Has control over Guest Network 4 (interface 36) :1048576
         Bit 21: -- Admin Has control over Guest Network 5 (interface 37) :2097152
         Bit 22: -- Admin Has control over Guest Network 6 (interface 38) :4194304
         Bit 23: -- Admin Has control over Guest Network 7 (interface 39) :8388608

         This object value is stored in non-vol and set to 1
         after factory reset."

    ::= { tchRgDot11ExtMgmtEntry 17 }

tchRgDot11ExtActualChannel OBJECT-TYPE
    SYNTAX      INTEGER
    MAX-ACCESS  read-only
    STATUS      current
    DESCRIPTION
        "Reports the current channel number that wireless is on.
         The value of 0 means wireless is disabled."
    ::= { tchRgDot11ExtMgmtEntry 18 }

tchRgDot11ExtOnOffPushButtonTime OBJECT-TYPE
    SYNTAX      INTEGER (0..11)
    UNITS       "seconds"
    MAX-ACCESS  read-write
    STATUS      current
    DESCRIPTION
        "Specifies how long to press WPS button to enable or disable
         the WiFi interface (primary SSID). When set to 11, the feature
         is disabled.
         Note that if the device has multiple radios but a single WPS HW button,
         only the first instance (tchRgDot11ExtOnOffPushButtonTime.32) should be used.
         Stored in non-vol, 5, 10 after factory reset."
    ::= { tchRgDot11ExtMgmtEntry 19 }

tchRgDot11ExtWmm OBJECT-TYPE
    SYNTAX  INTEGER {
        disable(0),
        enable(1)
        }
    MAX-ACCESS  read-write
    STATUS      current
    DESCRIPTION
        "Mib to Enable/Disable Wifi-Multi Media (WMM) QOS fetures.
        This parameter is stored in non-vol and set to
        enable(1) after a factory reset."
    DEFVAL { 1 }
    ::= { tchRgDot11ExtMgmtEntry 20 }

 tchRgDot11ExtWmmNoAck OBJECT-TYPE
    SYNTAX  INTEGER {
        disable(0),
        enable(1)
        }
    MAX-ACCESS  read-write
    STATUS      current
    DESCRIPTION
        "Mib to control whether Wifi packets require acknowledgement.
        disable(0) Use acknowledgemnet for Wifi packets.
        enable(1)  Sets No acknowledgement which allows for higher throughput and lower latency when some
                   packetloss is acceptable (ex. VoIP).
        Note: If WMM is disabled then this setting has no effect, and you can Not disable Acks from being
        returned from the stations.
        This parameter is stored in non-vol and set to disable(0) after a factory reset."
    DEFVAL { 0 }
    ::= { tchRgDot11ExtMgmtEntry 21 }

 tchRgDot11ExtMulticastRate OBJECT-TYPE
    SYNTAX      INTEGER {
                                disable(0),
                mbits1(1),
                mbits2(2),
                mbits5-5(5),
                mbits6(6),
                mbits9(9),
                mbits11(11),
                mbits12(12),
                mbits18(18),
                mbits24(24),
                mbits36(36),
                mbits48(48),
                mbits54(54)
        }
    UNITS       "Mbps"
    MAX-ACCESS  read-write
    STATUS      current
    DESCRIPTION
        "Forces the dot11 multicast Phy transmission rate.
         Note that the 802.11b rates, including mbits1(1), mbits2(2),
         mbits5-5(5), and mbits11(11), are not available in 5GHz.
         This object is stored in non-vol and defaults to disable(0) after factory reset."
    DEFVAL { 0 }
    ::= { tchRgDot11ExtMgmtEntry 22 }

tchRgDot11ExtWirelessButtonOperation OBJECT-TYPE
    SYNTAX  INTEGER {
        disable(0),
        enable(1)
    }
    MAX-ACCESS    read-write
    STATUS        current
    DESCRIPTION
        "To enable or disable the button press of wireless ON/OFF button.
         This feature will work only on products that have the wireless ON/OFF button.
         This MIB will control if the Wireless ON/OFF button can be pressed or not.
         If it's enabled then button press would take effect otherwise there will not be any effect on button press.
         Note that if the device has multiple radios but a single Wireless ON/OFF button,
         only the first instance (tchRgDot11ExtWirelessButtonOperation.32) should be used.
         By default value will be set to enable(1)."
    DEFVAL { 1 }
    ::= { tchRgDot11ExtMgmtEntry 23 }

tchRgDot11ExtWpsEnable OBJECT-TYPE
    SYNTAX  INTEGER {
        disable(0),
        enable(1)
    }
    MAX-ACCESS    read-write
    STATUS        current
    DESCRIPTION
        "To enable or disable WPS.
         This feature will work only on products that have WPS.
         Note that if the device has multiple radios but one WPS,
         only the first instance (tchRgDot11ExtWpsEnable.32) should be used."
    ::= { tchRgDot11ExtMgmtEntry 24 }

tchRgDot11ExtWpsPin OBJECT-TYPE
    SYNTAX  Integer32
    MAX-ACCESS    read-write
    STATUS        current
    DESCRIPTION
        "This MIB shows the current WPS PIN.
         Note that if the device has multiple radios but one WPS,
         only the first instance (tchRgDot11ExtWpsPin.32) should be used."
    ::= { tchRgDot11ExtMgmtEntry 25 }

tchRgDot11ExtForceRescan OBJECT-TYPE
    SYNTAX  INTEGER {
        true(1),
        false(2)
    }
    MAX-ACCESS    read-write
    STATUS        current
    DESCRIPTION
        "Setting this MIB to true will force a channel rescan of that radio if the radio channel is set to Auto.
         If a better channel is found, the radio must move to the new channel."
    DEFVAL { 2 }
    ::= { tchRgDot11ExtMgmtEntry 26 }

tchRgDot11ExtPowerSaveSupport OBJECT-TYPE
	SYNTAX INTEGER {
		true(1),
		false(2)
	}
	MAX-ACCESS read-write
	STATUS current
	DESCRIPTION
	"Enable/Disable the Power Save Support."
 
	DEFVAL { 1 }
	::= { tchRgDot11ExtMgmtEntry 27 }

tchRgDot11ExtWpsAPPinEnable OBJECT-TYPE
	SYNTAX INTEGER {
		true(1),
		false(2)
	}
	MAX-ACCESS read-write
	STATUS current
	DESCRIPTION
	"To enable or disable WPS AP Pin Method. This feature will work only on products that have WPS.
     Note that if the device has multiple radios but one WPS, only the first instance (tchRgDot11ExtWpsAPPinEnable.32) should be used."
 
	DEFVAL { 1 }
	::= { tchRgDot11ExtMgmtEntry 28 }
---------------------------------------
-- Dot11nExt - Radio Settings Table
---  Table to support Multiple 802.11n Radios
---  Note: Indexes may be set to support specific hardware interfaces.
---  Index 32 MUST match tchRgDot11n.
---------------------------------------

tchRgDot11nExt OBJECT IDENTIFIER ::= { tchRgDot11 7 }

tchRgDot11nExtTable  OBJECT-TYPE
    SYNTAX      SEQUENCE OF TchRgDot11nExtEntry
    MAX-ACCESS  not-accessible
    STATUS      current
    DESCRIPTION
        "Multiple 802.11n Radio Configuration Table
                 Index 32 should be set for Radio 0 -- 2.4 GHz if populated.
                 Index 112 should be set for Radio 1"
    ::= { tchRgDot11nExt 1 }

tchRgDot11nExtEntry OBJECT-TYPE
    SYNTAX      TchRgDot11nExtEntry
    MAX-ACCESS  not-accessible
    STATUS      current
    DESCRIPTION
        "A row in the table which represents parameters for an 802.11n Radio."
    INDEX   { ifIndex }
    ::= { tchRgDot11nExtTable 1 }

TchRgDot11nExtEntry ::=
    SEQUENCE {
                tchRgdot11nExtMode               INTEGER,
                tchRgdot11nExtPhyRate            INTEGER,
                tchRgdot11nExtBand               INTEGER,
                tchRgdot11nExtBandWidth          INTEGER,
                tchRgdot11nExtSideBand           INTEGER,
                tchRgdot11nExtObssCoex           INTEGER,
                tchRgdot11nExtMulticastRate      INTEGER,
                tchRgdot11nExtBSenable	         INTEGER,
                tchRgdot11nExtKeepRadioAlive     INTEGER,
                tchRgdot11nExtUNII2ExtChannelEnable     INTEGER
        }

tchRgdot11nExtMode OBJECT-TYPE
    SYNTAX INTEGER {
        auto(1),
        off(2),
        n-only(3),
        b-mode(16),
        g-mode(32),
        bg-mode(48),
        a-mode(64),
        n-only-bitmask(128),    -- to differentiate from n-only(3)
        gn-mode(160),
        bgn-mode(176),
        an-mode(192),
        ac-only(256),
        nac-only(384),
        anac-mode(448)
        }
    MAX-ACCESS  read-write
    STATUS      current
    DESCRIPTION
        "Determines which 802.11 mode the radio will run in.
         This object must be set by either the legacy or bitmask method.

         In legacy method,
         auto(1)  : supports all the 802.11 modes available in the radio.
         off(2)   : supports the legacy mode only (11b/g in 2.4GHz and 11a in 5GHz).
         n-only(3): accepts 11n-capable clients only but supports all the modes available in the radio.

         In bitmask method,
         b-mode(16)    : supports 11b mode in 2.4GHz.
         g-mode(32)    : supports 11g mode in 2.4GHz.
         bg-mode(48)   : supports 11b/g mode in 2.4GHz (16+32).
         a-mode(64)    : supports 11a mode in 5GHz.
         n-only-bitmask(128)   : accepts 11n-capable clients only but supports both legacy and 11n modes in 2.4GHz or 5GHz.
         gn-mode(160)  : supports 11g/n mode in 2.4GHz (32+128).
         bgn-mode(176) : supports all 11b/g/n modes in 2.4GHz (16+32+128).
         an-mode(192)  : supports 11a/n modes in 5GHz (64+128).
         ac-only(256)  : accepts 11ac-capable clients only but supports 11a/n/ac modes in 5GHz.
         nac-only(384) : accepts 11n-capable clients only but supports 11a/n/ac modes in 5GHz (128+256).
         anac-mode(448): supports all 11a/n/ac modes in 5GHz (64+128+256).

         Note: Some options may not be available depending on the radio model.
         Note: The change of this object value will also affect other MIB selections, including tchRgdot11nExtBandWidth.
         This object is stored in non-vol and defaults to auto(1) after factory reset."
     ::= { tchRgDot11nExtEntry 1 }

tchRgdot11nExtPhyRate OBJECT-TYPE
    SYNTAX INTEGER {
        auto(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the N Phy transmission rate for the AP to a particular speed.  Each pair of rates
         corresponds to a 20 MHz or 40 MHz channel configuration.
         This object is stored in non-vol and defaults to auto(0) after factory reset.

         This MIB is being degraded, since it is better for higher band width devices to run in 'auto' mode"
    DEFVAL { auto }
    ::= { tchRgDot11nExtEntry 2 }


tchRgdot11nExtBand OBJECT-TYPE
    SYNTAX INTEGER {
        band-2-4G(1),
        band-5G(2)
        }
    MAX-ACCESS  read-write
    STATUS      current
    DESCRIPTION
        "Determines which Band that we will be operating in. Either the 2.4G or the 5G Hz.
         Note: This is for N cards only.
         This object is stored in non-vol and defaults to band-2-4G(1) after factory reset."
    ::= { tchRgDot11nExtEntry 3 }

tchRgdot11nExtBandWidth OBJECT-TYPE
    SYNTAX INTEGER {
        width-20MHz(1),
        width-40MHz(2),
        width-80MHz(3)
        }
    MAX-ACCESS  read-write
    STATUS      current
    DESCRIPTION
        "Determines which Band Width that we will be operating in. Either the 20MHz or the 40MHz.
         Note: This is for N cards only, and this also affect other MIB selections such as tchRgdot11nSideBand.
         The 80 MHz channel width is only applicable for 802.11ac capable cards. If a user sets this to 80 MHz, SNMPset would fail for non-802.11ac cards
         This object is stored in non-vol and defaults to ? after factory reset."
    ::= { tchRgDot11nExtEntry 4 }

tchRgdot11nExtSideBand OBJECT-TYPE
    SYNTAX INTEGER {
        upper(1),
        lower(2)
        }
    MAX-ACCESS  read-write
    STATUS      current
    DESCRIPTION
        "Determines which side Band the channel will operate in.
         Note: This is for N cards only, this mib is dependent of what tchRgdot11nBandWidth is selected and only
         applies when 40MHz is selected.
         This object is stored in non-vol and defaults to lower(2) after factory reset."
    ::= { tchRgDot11nExtEntry 5 }

tchRgdot11nExtObssCoex OBJECT-TYPE
        SYNTAX INTEGER {
                disable(0),
                enable(1)
                }
        MAX-ACCESS read-write
        STATUS     current
        DESCRIPTION
                "Allows MSO to control OBSS (Overlapping BSS) Coexistance parameter for 802.11n 40MHz channel width.
                 By default it is enabled and is stored in non-vol
                 Factory reset would clear it and would be enable(1) after factory reset.
                 When disabled, the 802.11n Wifi would stay in 40 MHz channel-width inspite of interference from other
                 wifi channels. While enabled, 802.11n would coexist with 802.11g channels using 20 MHz default channel-width
                 "
        ::= { tchRgDot11nExtEntry 6 }

tchRgdot11nExtMulticastRate OBJECT-TYPE
    SYNTAX INTEGER {
        disable(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the dot11n Multicast Phy transmission rate.  Legacy mode forces the rate to be set
                 by dot11MulticastRate.
         This object is stored in non-vol and defaults to disable(0) after factory reset."
    DEFVAL { 0 }
    ::= { tchRgDot11nExtEntry 7 }

tchRgdot11nExtBSenable OBJECT-TYPE
    SYNTAX INTEGER {
        disable(0),
        enable(1)
        }
        MAX-ACCESS read-write
        STATUS     current
        DESCRIPTION
                "Controls and reflects the state of Wifi Radio's Band steering capability for all cards.  
				If set to enable(1), then Band steering will be enabled.
				Set to disable(0) to disable the Band steering feature."
		DEFVAL { 0 }
        ::= { tchRgDot11nExtEntry 8 }

tchRgdot11nExtKeepRadioAlive OBJECT-TYPE
    SYNTAX INTEGER {
        disable(0),
        enable(1)
        }
    MAX-ACCESS  read-write
    STATUS      current
    DESCRIPTION
        "When it is set to enable(1) and wireless button is pressed, Radio will be turned OFF irrespective of Hotspot
        SSIDs Enable state. When it is set to disable(0), Radio will be turned OFF only if HotSpot SSIDs Enable state 
        is disabled. Default value is enable(1) and is stored in non-vol. Factory reset would clear it and would be 
        enable(1) after factory reset."
    DEFVAL { 1 }
    ::= { tchRgDot11nExtEntry 9 }

tchRgdot11nExtUNII2ExtChannelEnable OBJECT-TYPE
    SYNTAX INTEGER {
        disable(0),
        enable(1)
        }
    MAX-ACCESS  read-write
    STATUS      current
    DESCRIPTION
        "When it is set to disable(0) UNII2-Ext channels are removed from Auto channel selection.
         When it is set to enable(1) UNII2-Ext channels are included in Auto channel selection.
         Default value is disable(0) and is stored in non-vol. Factory reset would clear it and would be 
         disable(0) after factory reset.
         
         UNII2-Ext channels are 100, 104, 108, 112, 116, 120, 124, 128, 132, 136, 140, 144
         This is applicable for 5GHz radio only.        
         "
    DEFVAL { 0 }
    ::= { tchRgDot11nExtEntry 10 }

-------------------------------------------------
-- Table to get the status of the Wifi driver
-- from the file in nvram(.wifi5gdisabled).
-- The file in nvram is updated at boot up,
-- based of a wifi Mitigation logic provided by BRCM.
-- Currently the need is only for 5G but creating
-- tabular MIB for future use.
-------------------------------------------------
tchRgDot11ReadRadioStatus OBJECT IDENTIFIER ::= { tchRgDot11 8 }

tchRgDot11RadioStatusTable  OBJECT-TYPE
    SYNTAX      SEQUENCE OF TchRgDot11RadioStatusEntry
    MAX-ACCESS  not-accessible
    STATUS      current
    DESCRIPTION
        "Multiple 802.11n Radio Status Table
                 Index 10000 should be set for Radio 0 -- 2.4 GHz if populated.
                 Index 10100 should be set for Radio 1"
    ::= { tchRgDot11ReadRadioStatus 1 }

tchRgDot11RadioStatusEntry OBJECT-TYPE
    SYNTAX      TchRgDot11RadioStatusEntry
    MAX-ACCESS  not-accessible
    STATUS      current
    DESCRIPTION
        "A row in the table which represents parameters for an 802.11n Radio."
    INDEX   { ifIndex }
    ::= { tchRgDot11RadioStatusTable 1 }

TchRgDot11RadioStatusEntry ::=
    SEQUENCE {
                tchRgdot11WifiRadioStatus               INTEGER,
        }

tchRgdot11WifiRadioStatus OBJECT-TYPE
    SYNTAX INTEGER
    MAX-ACCESS  read-only
    STATUS      current
    DESCRIPTION 
	"Returns the status value of 5g wifi card. 
	Possible Return Values are 0,1,2.
	0 - Indicates a Good Wifi Card and 1 - Indicates a Bad Wifi Card.
	2 - Indicates as Not Supported."
     ::= { tchRgDot11RadioStatusEntry 1 }


---------------------------------------
-- tchRgDot11SuperWifi - SuperWifi Cloud AuthConfig management for Vodafone
---  AccountID , URL and password set/get
---  Some reports on Certificates and AuthConfig
---------------------------------------

tchRgDot11SuperWifi   OBJECT IDENTIFIER ::= { tchRgDot11 9 }


tchRgDot11SuperWifiControlMode OBJECT-TYPE
    SYNTAX INTEGER {
        dormant(1),
        passive(2),
        passivePlus(3),
        active(4)
        }
    MAX-ACCESS  read-write
    STATUS      current
    DESCRIPTION
        "dormant(1) - Super Wi-Fi is Off
        passive(2) - Super Wi-Fi will collect telemetry data, but will not affect any changes
        passivePlus(3) - Super Wi-Fi will collect telemetry data and manage GW AP configuration.
        active(4) - Super Wi-Fi is in control of the system's Wi-Fi
        If the Super Wi-Fi is in active mode and the gateway receives a CM ConfigFile with the MIB set to passive(2) mode,
        the gateway must ignore the MIB and stay in active mode.
        All other mode transitions are allowed.
        This object is stored in non-vol and defaults to dormant(1) after factory reset."
    DEFVAL { 1 }
    ::= { tchRgDot11SuperWifi 1 }

tchRgDot11SuperWifiIPAddress OBJECT-TYPE
    SYNTAX SnmpAdminString
    MAX-ACCESS read-only
    STATUS current
    DESCRIPTION
        "This field contains the ip address of the URL for the cloud."
    ::= { tchRgDot11SuperWifi 2 }

tchRgDot11SuperWifiURL OBJECT-TYPE
SYNTAX SnmpAdminString
MAX-ACCESS read-write
STATUS current
DESCRIPTION
    "This field sets the Authentication URL of the WiFi Conductor to the CPE."
::= { tchRgDot11SuperWifi 3 }

tchRgDot11SuperWifiAuthPassword OBJECT-TYPE
SYNTAX SnmpAdminString
MAX-ACCESS read-write
STATUS current
DESCRIPTION
    "This field sets the Authentication password of the WiFi Doctor Agent to the CPE."
::= { tchRgDot11SuperWifi 4 }

tchRgDot11SuperWifiCertSubject OBJECT-TYPE
SYNTAX SnmpAdminString
MAX-ACCESS read-only
STATUS current
DESCRIPTION
    "Value that can be read as per result of Onboarding procedure."
::= { tchRgDot11SuperWifi 5 }

tchRgDot11SuperWifiCertSerialNumber OBJECT-TYPE
SYNTAX SnmpAdminString
MAX-ACCESS read-only
STATUS current
DESCRIPTION
    "Value that can be read as per result of Onboarding procedure."
::= { tchRgDot11SuperWifi 6 }

tchRgDot11SuperWifiCertSerialNotBefore OBJECT-TYPE
SYNTAX SnmpAdminString
MAX-ACCESS read-only
STATUS current
DESCRIPTION
    "Value that can be read as per result of Onboarding procedure."
::= { tchRgDot11SuperWifi 7 }

tchRgDot11SuperWifiCertHomeID OBJECT-TYPE
SYNTAX SnmpAdminString
MAX-ACCESS read-only
STATUS current
DESCRIPTION
    "Value that can be read as per result of Onboarding procedure."
::= { tchRgDot11SuperWifi 8 }

tchRgDot11SuperWifiCertIssuer OBJECT-TYPE
SYNTAX SnmpAdminString
MAX-ACCESS read-only
STATUS current
DESCRIPTION        "Value that can be read as per result of Onboarding procedure."
::= { tchRgDot11SuperWifi 9 }

tchRgDot11SuperWifiCertNotAfter OBJECT-TYPE
SYNTAX SnmpAdminString
MAX-ACCESS read-only
STATUS current
DESCRIPTION        "Value that can be read as per result of Onboarding procedure."
::= { tchRgDot11SuperWifi 10 }

tchRgDot11SuperWifiRoamerMACACLEnabled OBJECT-TYPE
SYNTAX TruthValue
MAX-ACCESS read-write
STATUS current
DESCRIPTION
   "This field allows the local market to enable/disable forceful band and client steering via MAC ACL."
DEFVAL {  false }
::= { tchRgDot11SuperWifi 11 }

tchRgDot11SuperWifiCertRegStatus OBJECT-TYPE
SYNTAX SnmpAdminString
MAX-ACCESS read-only
STATUS current
DESCRIPTION        "Value that can be read as per result of Onboarding procedure."
::= { tchRgDot11SuperWifi 12 }

-- tchRgDot11ApplySettings: do 'on the fly' config with settings from above.
-- This scalar object was placed by itself at ieee802tchRgDot11Mgmt 100 because
-- it applies all settings from all current and possibly future 802.11
-- groups.  Wanted to leave plenty of room to add new groups in the future.

tchRgDot11ApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until tchRgDot11ApplySettings is set to true or CM resets.
         Note: this applies only to the MIB objects that are stored
         in non-vol.
         Always returns false(2) when read."
    ::= { tchRgDot11 1001 }


-- =============
-- IP management
-- =============

tchRgIpMgmt OBJECT IDENTIFIER ::=  { tchRg 3 }


-- { tchRgIpMgmt 1 } reserved for WAN IP definition (currently only DHCP)


-- LAN NETWORK DEFINITIONS

tchRgIpMgmtLanTable OBJECT-TYPE
    SYNTAX SEQUENCE OF TchRgIpMgmtLanEntry
    MAX-ACCESS not-accessible
    STATUS current
    DESCRIPTION
            "Networks on the LAN side.
             Primary BSS stored in non-vol."
    ::= { tchRgIpMgmt 2 }

tchRgIpMgmtLanEntry OBJECT-TYPE
    SYNTAX      TchRgIpMgmtLanEntry
    MAX-ACCESS  not-accessible
    STATUS     current
    DESCRIPTION
            "List of networks on the LAN side."
    INDEX { ifIndex }
    ::= { tchRgIpMgmtLanTable 1 }

TchRgIpMgmtLanEntry ::= SEQUENCE {
    tchRgIpMgmtLanMode              INTEGER,
    tchRgIpMgmtLanNetwork           IpAddress,
    tchRgIpMgmtLanNetworksAllow     INTEGER,
    tchRgIpMgmtLanSubnetMask        IpAddress,
    tchRgIpMgmtLanGateway           IpAddress,
    tchRgIpMgmtLanDhcpServer        INTEGER,
    tchRgIpMgmtLanNapt              INTEGER,
    tchRgIpMgmtLanTypeOfService     INTEGER,
    tchRgIpMgmtLanDhcp125Option     INTEGER,
    tchRgIpMgmtLanHnap                  INTEGER,
        tchRgIpMgmtLanUpnp                          INTEGER,
        tchRgIpMgmtLanDhcpOption43      SnmpAdminString
    }

tchRgIpMgmtLanMode OBJECT-TYPE
    SYNTAX INTEGER {
        bridge(1),
        router(2),
        l2tpv2-client(3),
        mixed(4),
        vlan(5)
        }
    MAX-ACCESS    read-write
    STATUS        current
    DESCRIPTION
        "Defines the mode of operation for the device.
        Setting this object via SNMP for the primary BSS will cause
        the unit to reboot.
        Setting this object via SNMP for the secondary BSSs will not
        cause the unit to reboot.
        The value for primary BSS is stored in non-vol and is router
        after factory reset.
        The default value for other BSSs is router.
                This MIB supersedes tchRgDeviceMode for the .32 interface.
        l2tpv2-client(3)is obsoleted and NOT supported.

                bridge(1):      Sets individual interface to bridging mode
                                        (for IPv6 interfaces DHCPv6 is external)
                router(2):      Sets individual interface to routing mode
                                        (for IPv6 interfaces DHCPv6 is internal)
                l2tpv2-client(3): <obsolete>
                mixed(4):       For mixed mode. This setting is applicable only to
                                        .32 interface. This value is used on conjunction with
                                        tchRgIpMgmtLanPortControlTable
                                        *Note: mixed(4) mode NOT Supported by DOCSIS 2.0 products.
                vlan (5):       Enables the vlan control feature.
                                        See tchRgVlanTable MIBs for VLAN configuration information."
    DEFVAL { 2 }
    ::= { tchRgIpMgmtLanEntry 1 }

tchRgIpMgmtLanNetwork OBJECT-TYPE
    SYNTAX      IpAddress
    MAX-ACCESS  read-write
    STATUS      current
    DESCRIPTION
            "The LAN-Trans network number.
            Default for primary BSS is 192.168.0.0
            Default for other BSSs is 192.168.ifIndex.0"
    ::= { tchRgIpMgmtLanEntry 3 }


tchRgIpMgmtLanNetworksAllow OBJECT-TYPE
                SYNTAX  INTEGER {
                default(0),
                anyPrivateClass(1),
                anyClass(2)
        }
    MAX-ACCESS  read-write
    STATUS      current
    DESCRIPTION
                "Allows the user via the internal Web GUI (Lan Setup page
                to input an IPv4 public or private Local IP address other than a
                class C Private address (the default Network for the Primary BSS = 192.168.0.0/24, with
                the default Local Ip address = 192.168.0.1.)
                In all cases the mask must be 255.255.255.x since the RG is limited to supporting
                a maximum of 253 IP addresses.
                (See RFC1918 for a description of private IP addresses and specified ranges.)
                Available Mib settings:
                default(0):                     Only the third and fourth octets are editable in
                                                        the Web GUI for the Local IP address (Ex. 192.168.x.x/24).
                anyPrivateClass(1):     All 4 octets are editable in the Web GUI for Local IP address, but
                                                        the network specified must be a Private class A, B or C network address.
                                                        (Ex. A=10.x.x.x, B=172.16.x.x, C=192.168.x.x).
                anyClass(2):            All 4 octets are editable in the Web GUI for Local IP address, and
                                                        the network specified could be any public or private class A, B, or C address.

                If the MSO specifically sets a Local IP address in tchRgIpMgmtLanNetwork to a value other than
                the default value (for example: 192.168.0.1) then these fields will be uneditable by the user (grayed out)."
        DEFVAL { 0 }
        ::= { tchRgIpMgmtLanEntry 4 }

tchRgIpMgmtLanSubnetMask OBJECT-TYPE
    SYNTAX      IpAddress
    MAX-ACCESS  read-write
    STATUS      current
    DESCRIPTION
            "The device MUST provide the value of this MIB
            object in the Option 1 (Subnet Mask) of
            DHCP OFFER and ACK messages sent to a LAN IP Device."
    DEFVAL { 'ffffff00'h }    -- 255.255.255.0
    ::= { tchRgIpMgmtLanEntry 5 }

tchRgIpMgmtLanGateway OBJECT-TYPE
    SYNTAX      IpAddress
    MAX-ACCESS  read-write
    STATUS      current
    DESCRIPTION
                "The type of this address is specified by
            tchRgIpMgmtLanNetwokRouterType. The PS MUST
            provide the value of this MIB object in the
            Option 3 (Router IP address) of the DHCP
            OFFER and ACK messages sent to the LAN IP Device.
            Default for primary BSS is 192.168.0.1
            Default for other BSSs is 192.168.ifIndex.1"
    ::= { tchRgIpMgmtLanEntry 7 }

tchRgIpMgmtLanDhcpServer OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { tchRgIpMgmtLanEntry 8 }

tchRgIpMgmtLanNapt OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { tchRgIpMgmtLanEntry 9 }

tchRgIpMgmtLanTypeOfService OBJECT-TYPE
      SYNTAX      INTEGER
      MAX-ACCESS  read-write
      STATUS      current
      DESCRIPTION
          "Definition of the TOS bits for the Network.
           This object does not apply to primary BSS."
      DEFVAL { 0 }
      ::= { tchRgIpMgmtLanEntry 10 }

tchRgIpMgmtLanDhcp125Option OBJECT-TYPE
      SYNTAX      INTEGER {
        disable(0),
        addSsidName(1)
        }
      MAX-ACCESS  read-write
      STATUS      current
      DESCRIPTION
          "This option controls if the RG adds a Technicolor specific
           suboption (number 17) to DHCP DISCOVER and REQUEST
           from the clients that are bridged on the BSS:
         0: do not add the option
         1: add suboption 17 to Technicolor specific enterprise-id
            (9) within DHCP option 125. The content is the SSID name."
      DEFVAL { 0 }
      ::= { tchRgIpMgmtLanEntry 11 }

tchRgIpMgmtLanHnap OBJECT-TYPE
    SYNTAX INTEGER {
        disable(0),
        enable(1)
        }
    MAX-ACCESS    read-write
    STATUS        current
    DESCRIPTION
        "The value for primary BSS is stored in non-vol and
         is enable after factory default.
         The default value for other BSSs is disable."
    ::= { tchRgIpMgmtLanEntry 12 }

tchRgIpMgmtLanUpnp OBJECT-TYPE
    SYNTAX INTEGER {
        disable(0),
        enable(1)
        }
    MAX-ACCESS    read-write
    STATUS        current
    DESCRIPTION
        "Enable/Disable the UPnP agent.
             The value is stored in non-vol and is disabled after factory default for the primary SSID.
                     The UPnP agents for additional networks are enabled by default.
         "
    DEFVAL { 0 }
    ::= { tchRgIpMgmtLanEntry 13 }

tchRgIpMgmtLanDhcpOption43 OBJECT-TYPE
    SYNTAX      SnmpAdminString
    MAX-ACCESS  read-write
    STATUS      current
    DESCRIPTION
         "If option 60 is set from the CPE then return this value in option 43 of the DHCP Reply.
         If this value is null then do not reply with option 43 (default is null)
         This MIB will apply to the Primary SSID (intface .32) only"
    ::= { tchRgIpMgmtLanEntry 14 }

-- LAN DHCP SERVERS DEFINITIONS

tchRgIpMgmtLanDhcpServerTable OBJECT-TYPE
    SYNTAX SEQUENCE OF TchRgIpMgmtLanDhcpServerEntry
    MAX-ACCESS not-accessible
    STATUS current
    DESCRIPTION
            "Networks on the LAN side.
             Stored in non-vol. .10-.128 for primary BSS
             after factory reset."
    ::= { tchRgIpMgmt 3 }

tchRgIpMgmtLanDhcpServerEntry OBJECT-TYPE
    SYNTAX      TchRgIpMgmtLanDhcpServerEntry
    MAX-ACCESS  not-accessible
    STATUS     current
    DESCRIPTION
            "List of networks on the LAN side."
    INDEX { ifIndex }
    ::= { tchRgIpMgmtLanDhcpServerTable 1 }

TchRgIpMgmtLanDhcpServerEntry ::= SEQUENCE {
    tchRgIpMgmtLanDhcpServerPoolStart         IpAddress,
    tchRgIpMgmtLanDhcpServerPoolEnd           IpAddress,
    tchRgIpMgmtLanDhcpServerLeaseTime         Unsigned32,
    tchRgIpMgmtLanDhcpServerTimeOffset        Integer32,
        tchRgIpMgmtLanDhcpServerDomainName        SnmpAdminString
    }


tchRgIpMgmtLanDhcpServerPoolStart OBJECT-TYPE
    SYNTAX      IpAddress
    MAX-ACCESS  read-write
    STATUS      current
    DESCRIPTION
            "The start of range LAN Trans IP Addresses. The type of
            this address is specified by tchRgIpMgmtLanDhcpServerPoolStartType.
            Default value depends on IP network and subnet."
    ::= { tchRgIpMgmtLanDhcpServerEntry 2 }

tchRgIpMgmtLanDhcpServerPoolEnd OBJECT-TYPE
    SYNTAX      IpAddress
    MAX-ACCESS  read-write
    STATUS      current
    DESCRIPTION
            "The end of range for LAN-Trans IP Addresses. The type of
            this address is specified by tchRgIpMgmtLanDhcpServerPoolEndType.
            Default value depends on IP network and subnet."
    ::= { tchRgIpMgmtLanDhcpServerEntry 4 }

tchRgIpMgmtLanDhcpServerLeaseTime OBJECT-TYPE
    SYNTAX      Unsigned32
    UNITS       "seconds"
    MAX-ACCESS  read-write
    STATUS      current
    DESCRIPTION
            "The PS MUST provide the value of this MIB object in the
            Option 51 (IP Address lease time) of the DHCP OFFER and
            ACK messages sent to the LAN IP Device."
    DEFVAL { 3600 }
    ::= { tchRgIpMgmtLanDhcpServerEntry 5 }

tchRgIpMgmtLanDhcpServerTimeOffset OBJECT-TYPE
    SYNTAX      Integer32 (-86400..86400) -- 0 to 24 hours (in seconds)
    UNITS       "seconds"
    MAX-ACCESS  read-write
    STATUS      current
    DESCRIPTION
            "The PS MUST provide the value of this MIB object in
            the Option 2 (Time Offset from Coordinated
            Universal Time-UTC) in the DHCP OFFER and ACK
            messages sent to the LAN IP Device."
    DEFVAL { 0 }    -- UTC
    ::= { tchRgIpMgmtLanDhcpServerEntry 6 }

tchRgIpMgmtLanDhcpServerDomainName OBJECT-TYPE
    SYNTAX      SnmpAdminString
    MAX-ACCESS  read-write
    STATUS      current
    DESCRIPTION
            "This is the domain name given to this DHCP server's clients."
    ::= { tchRgIpMgmtLanDhcpServerEntry 7 }

--====================================================================
--
--    tchRgIpMgmtLanAddrTable (CDP LAN Address Table)
--
--    The tchRgIpMgmtLanAddrTable contains the DHCP parameters
--    for each IP address served to the LAN-Trans realm.
--
--=========================================================================

tchRgIpMgmtLanAddrTable OBJECT-TYPE
       SYNTAX      SEQUENCE OF TchRgIpMgmtLanAddrEntry
       MAX-ACCESS  not-accessible
       STATUS      current
       DESCRIPTION
               "IP addresses of devices served by DHCP servers."
    ::= { tchRgIpMgmt 4 }

tchRgIpMgmtLanAddrEntry OBJECT-TYPE
    SYNTAX      TchRgIpMgmtLanAddrEntry
    MAX-ACCESS  not-accessible
    STATUS      current
    DESCRIPTION
            "List of general parameters pertaining to LAN-Trans IP
            address reservations and leases."
    INDEX { ifIndex, tchRgIpMgmtLanAddrIndex }
    ::= { tchRgIpMgmtLanAddrTable 1 }

TchRgIpMgmtLanAddrEntry ::= SEQUENCE {
    tchRgIpMgmtLanAddrIndex              INTEGER,
    tchRgIpMgmtLanAddrIp                 IpAddress,
    tchRgIpMgmtLanAddrPhysAddr           PhysAddress,
    tchRgIpMgmtLanAddrLeaseCreateTime    DateAndTime,
    tchRgIpMgmtLanAddrLeaseExpireTime    DateAndTime,
    tchRgIpMgmtLanAddrHostName           SnmpAdminString,
    tchRgIpMgmtLanAddrClientId           SnmpAdminString,
    tchRgIpMgmtLanAddrInterface          SnmpAdminString,
        tchRgIpMgmtLanAddrClientNotes        SnmpAdminString,
        tchRgIpMgmtLanAddrCpeStatus          INTEGER,
            tchRgIpMgmtLanAddrSignalStrength     Integer32,
        tchRgIpMgmtLanAddrRequestedOptionsList OCTET STRING,
        tchRgIpMgmtLanAddrParameterRequestList OCTET STRING

    }

tchRgIpMgmtLanAddrIndex OBJECT-TYPE
    SYNTAX      INTEGER (0..255)
    MAX-ACCESS  not-accessible
    STATUS      current
    DESCRIPTION
            "The index of the the LAN IP Device in the LAN-Trans Realm."
    ::= { tchRgIpMgmtLanAddrEntry 1 }

tchRgIpMgmtLanAddrIp OBJECT-TYPE
    SYNTAX      IpAddress
    MAX-ACCESS  read-only
    STATUS      current
    DESCRIPTION
            ""
    ::= { tchRgIpMgmtLanAddrEntry 3 }

tchRgIpMgmtLanAddrPhysAddr OBJECT-TYPE
    SYNTAX      PhysAddress
    MAX-ACCESS  read-only
    STATUS      current
    DESCRIPTION
            "The client's (i.e., LAN IP Device's) hardware address as
            indicated in the chaddr field of its DHCP REQUEST message."
    ::= { tchRgIpMgmtLanAddrEntry 4 }

tchRgIpMgmtLanAddrLeaseCreateTime OBJECT-TYPE
    SYNTAX      DateAndTime
    MAX-ACCESS  read-only
    STATUS      current
    DESCRIPTION
            "This is the date and time when the LAN IP lease was
            created (if it has not yet been renewed) or last renewed."
    ::= { tchRgIpMgmtLanAddrEntry 5 }

tchRgIpMgmtLanAddrLeaseExpireTime OBJECT-TYPE
    SYNTAX      DateAndTime
    MAX-ACCESS  read-only
    STATUS      current
    DESCRIPTION
            "This is the date and time when the LAN IP address lease
            expired or will expire."
    ::= { tchRgIpMgmtLanAddrEntry 6 }


tchRgIpMgmtLanAddrHostName OBJECT-TYPE
    SYNTAX      SnmpAdminString
    MAX-ACCESS  read-only
    STATUS      current
    DESCRIPTION
            "This is the Host Name of the LAN IP address, based on DCHP
            option 12."
    ::= { tchRgIpMgmtLanAddrEntry 7 }

tchRgIpMgmtLanAddrClientId OBJECT-TYPE
    SYNTAX      SnmpAdminString
    MAX-ACCESS  read-only
    STATUS      current
    DESCRIPTION
            "This is the Client Class Identifier, based on DHCP option 60."
    ::= { tchRgIpMgmtLanAddrEntry 8 }

tchRgIpMgmtLanAddrInterface OBJECT-TYPE
    SYNTAX      SnmpAdminString
    MAX-ACCESS  read-only
    STATUS      current
    DESCRIPTION
            "This will show the associated interface (LAN, WiFi or MoCA) of the connected CPE."
    ::= { tchRgIpMgmtLanAddrEntry 9 }

tchRgIpMgmtLanAddrClientNotes OBJECT-TYPE
    SYNTAX      SnmpAdminString
    MAX-ACCESS  read-only
    STATUS      current
    DESCRIPTION
            "This will show the associated client notes for the connected CPE."
    ::= { tchRgIpMgmtLanAddrEntry 10 }

tchRgIpMgmtLanAddrCpeStatus OBJECT-TYPE
    SYNTAX INTEGER {
        offline(0),
        online(1)
        }
    MAX-ACCESS    read-only
    STATUS        current
    DESCRIPTION
        "This MIB shows the client's current online status.
                - 0 - The client currently has no connectivity.
                - 1 - The client currently has connectivity and is online.
                "
    DEFVAL { 0 }
    ::= { tchRgIpMgmtLanAddrEntry 11 }

    tchRgIpMgmtLanAddrSignalStrength OBJECT-TYPE
    SYNTAX      Integer32
    MAX-ACCESS  read-only
    STATUS      current
    DESCRIPTION
            "Signal strength of wireless LAN clients in dBm. This should be blank for wired clients."
    ::= { tchRgIpMgmtLanAddrEntry 12 }

tchRgIpMgmtLanAddrRequestedOptionsList OBJECT-TYPE
    SYNTAX      OCTET STRING
    MAX-ACCESS  read-only
    STATUS      current
    DESCRIPTION
            "The list of requested DHCP options in the client's DHCP Discover. This should be blank if the DHCP Discover contained no requested options."
    ::= { tchRgIpMgmtLanAddrEntry 13 }

tchRgIpMgmtLanAddrParameterRequestList OBJECT-TYPE
    SYNTAX      OCTET STRING
    MAX-ACCESS  read-only
    STATUS      current
    DESCRIPTION
            "The contents of option 55 in the client's DHCP Discover. This should be blank if the DHCP Discover contained no Option 55."
    ::= { tchRgIpMgmtLanAddrEntry 14 }

--===================================================================
--
-- tchRgIpMgmtDnsServerTable (CDP WAN DNS Server Table)
--
-- The tchRgIpMgmtDnsServerTable is a table of 3 cable network
-- and Internet DNS Servers.
--
--===================================================================

tchRgIpMgmtDnsServerTable OBJECT-TYPE
    SYNTAX SEQUENCE OF TchRgIpMgmtDnsServerEntry
    MAX-ACCESS not-accessible
    STATUS current
    DESCRIPTION
            "This table contains the IP addresses of cable network and
            Internet DNS servers, in the order of preference in which
            the PS's CNP will query them, when it cannot resolve a DNS
            query using local information. Entries in this table are
            updated with the information contained in DHCP Option 6,
            received during both the WAN-Man and WAN-Data IP
            acquisition processes.
            Stored in non-vol and 0.0.0.0 for all servers after
            factory reset."
    ::= { tchRgIpMgmt 5 }

tchRgIpMgmtDnsServerEntry OBJECT-TYPE
    SYNTAX      TchRgIpMgmtDnsServerEntry
    MAX-ACCESS  not-accessible
    STATUS     current
    DESCRIPTION
            "List of cable network and Internet DNS servers."
    INDEX { tchRgIpMgmtDnsServerOrder }
    ::= { tchRgIpMgmtDnsServerTable 1 }

TchRgIpMgmtDnsServerEntry ::= SEQUENCE {
    tchRgIpMgmtDnsServerOrder  INTEGER,
    tchRgIpMgmtDnsServerIp     IpAddress,
    tchRgIpMgmtDnsServerIpv6   InetAddress
    }

tchRgIpMgmtDnsServerOrder OBJECT-TYPE
    SYNTAX      INTEGER {
                    primary(1),
                    secondary(2),
                    tertiary(3)
                }
    MAX-ACCESS  not-accessible
    STATUS      current
    DESCRIPTION
            "The order of preference for cable network and Internet DNS
            servers, as listed in DHCP option 6 (Domain Server)."
    ::= { tchRgIpMgmtDnsServerEntry 1 }

tchRgIpMgmtDnsServerIp OBJECT-TYPE
    SYNTAX      IpAddress
    MAX-ACCESS  read-write
    STATUS      current
    DESCRIPTION
            "This parameter indicates the IP address of a WAN DNS
            server."
    ::= { tchRgIpMgmtDnsServerEntry 3 }

tchRgIpMgmtDnsServerIpv6 OBJECT-TYPE
    SYNTAX      InetAddress
    MAX-ACCESS  read-write
    STATUS      current
    DESCRIPTION
            "This parameter indicates the IPv6 address of a WAN DNS
            server."
    ::= { tchRgIpMgmtDnsServerEntry 4 }

--==============================
-- LAN DHCP fixed IP assignments
--==============================

tchRgIpMgmtDhcpFixedIpTable OBJECT-TYPE
    SYNTAX      SEQUENCE OF TchRgIpMgmtDhcpFixedIpEntry
    MAX-ACCESS  not-accessible
    STATUS      current
    DESCRIPTION
        "Fixed IP address assignments for DHCP server.
         Table does not return any row if DHCP disabled.
         The value for primary BSS is stored in non-vol."
    ::= { tchRgIpMgmt 6 }

tchRgIpMgmtDhcpFixedIpEntry OBJECT-TYPE
    SYNTAX      TchRgIpMgmtDhcpFixedIpEntry
    MAX-ACCESS  not-accessible
    STATUS      current
    DESCRIPTION
            "List of general parameters pertaining to LAN-Trans IP
            address reservations and leases."
    INDEX { ifIndex, tchRgIpMgmtDhcpFixedIpIndex }
    ::= { tchRgIpMgmtDhcpFixedIpTable 1 }

TchRgIpMgmtDhcpFixedIpEntry ::= SEQUENCE {
    tchRgIpMgmtDhcpFixedIpIndex              INTEGER,
    tchRgIpMgmtDhcpFixedIpRowStatus          RowStatus,
    tchRgIpMgmtDhcpFixedIpAddress            IpAddress,
    tchRgIpMgmtDhcpFixedIpPhysAddr           PhysAddress,
    tchRgIpMgmtDhcpFixedIpHostName           SnmpAdminString,
	tchRgIpMgmtDhcpFixedIpRemove			 INTEGER
    }

tchRgIpMgmtDhcpFixedIpIndex OBJECT-TYPE
    SYNTAX      INTEGER (1..16)
    MAX-ACCESS  not-accessible
    STATUS      current
    DESCRIPTION
            "The index of the the LAN IP Device in the LAN-Trans Realm."
    ::= { tchRgIpMgmtDhcpFixedIpEntry 1 }

tchRgIpMgmtDhcpFixedIpRowStatus OBJECT-TYPE
    SYNTAX      RowStatus
    MAX-ACCESS  read-write
    STATUS      current
    DESCRIPTION
            "The row status. A row can be destroyed."
    ::= { tchRgIpMgmtDhcpFixedIpEntry 2 }

tchRgIpMgmtDhcpFixedIpAddress OBJECT-TYPE
    SYNTAX      IpAddress
    MAX-ACCESS  read-write
    STATUS      current
    DESCRIPTION
            ""
    ::= { tchRgIpMgmtDhcpFixedIpEntry 4 }

tchRgIpMgmtDhcpFixedIpPhysAddr OBJECT-TYPE
    SYNTAX      PhysAddress
    MAX-ACCESS  read-create
    STATUS      current
    DESCRIPTION
            "The client's (i.e., LAN IP Device's) hardware address as
            indicated in the chaddr field of its DHCP REQUEST message."
    ::= { tchRgIpMgmtDhcpFixedIpEntry 5 }

tchRgIpMgmtDhcpFixedIpHostName OBJECT-TYPE
    SYNTAX      SnmpAdminString(SIZE(0..80))
    MAX-ACCESS  read-write
    STATUS      current
    DESCRIPTION
            "This is the Host Name of the LAN IP address, based on DCHP
            option 12."
    ::= { tchRgIpMgmtDhcpFixedIpEntry 6 }

tchRgIpMgmtDhcpFixedIpRemove OBJECT-TYPE
    SYNTAX      INTEGER {
                      false  (0),
                      true   (1),
                      all    (99)
                        }

      MAX-ACCESS    read-write
      STATUS        current
      DESCRIPTION
        "The default value is false(0).
         If set to true(1), then this IP reservation rule will be removed.
         If set to 99, then All IP reservation rules will be removed."
      ::= { tchRgIpMgmtDhcpFixedIpEntry 7 }

-- ==============
-- NAT parameters

tchRgIpMgmtNat OBJECT IDENTIFIER ::=  { tchRgIpMgmt 7 }

tchRgIpMgmtNatTcpWait OBJECT-TYPE
    SYNTAX      Unsigned32 (1..65535)
    UNITS       "seconds"
    MAX-ACCESS  read-write
    STATUS      current
    DESCRIPTION
        "Configures the NAT session time for TCP in seconds.
         Stored in non-vol, set to 300 after factory reset."
    ::= { tchRgIpMgmtNat 1 }

tchRgIpMgmtNatUdpWait OBJECT-TYPE
    SYNTAX      Unsigned32 (1..65535)
    UNITS       "seconds"
    MAX-ACCESS  read-write
    STATUS      current
    DESCRIPTION
        "Configures the NAT session time for UDP in seconds.
         Stored in non-vol, set to 300 after factory reset."
    ::= { tchRgIpMgmtNat 2 }

tchRgIpMgmtNatIcmpWait OBJECT-TYPE
    SYNTAX      Unsigned32 (1..65535)
    UNITS       "seconds"
    MAX-ACCESS  read-write
    STATUS      current
    DESCRIPTION
        "Configures the NAT session time for ICMP in seconds.
         Stored in non-vol, set to 2 after factory reset."
    ::= { tchRgIpMgmtNat 3 }         
    
tchRgIpMgmtNatSipAlg OBJECT-TYPE
    SYNTAX      TruthValue
    MAX-ACCESS  read-write
    STATUS      current
    DESCRIPTION
        "If set to false(2), then SIP ALG is disabled. This MIB is not available for all products"
    DEFVAL { false }
    ::= { tchRgIpMgmtNat 4 }


-- ==============
-- Static routing

tchRgIpMgmtStaticRouteTable OBJECT-TYPE
    SYNTAX SEQUENCE OF TchRgIpMgmtStaticRouteEntry
    MAX-ACCESS not-accessible
    STATUS current
    DESCRIPTION
        "Static route entries in the routing table.
         This table is saved in non-vol and is empty
         after factory reset."
    ::= { tchRgIpMgmt 8 }

tchRgIpMgmtStaticRouteEntry OBJECT-TYPE
    SYNTAX      TchRgIpMgmtStaticRouteEntry
    MAX-ACCESS  not-accessible
    STATUS     current
    DESCRIPTION
        "List of static route entries in the routing table."
    INDEX { tchRgIpMgmtStaticRouteIndex }
    ::= { tchRgIpMgmtStaticRouteTable 1 }

TchRgIpMgmtStaticRouteEntry ::= SEQUENCE {
    tchRgIpMgmtStaticRouteIndex         INTEGER,
    tchRgIpMgmtStaticRouteRowStatus     RowStatus,
    tchRgIpMgmtStaticRouteNetwork       IpAddress,
    tchRgIpMgmtStaticRouteSubnetMask    IpAddress,
    tchRgIpMgmtStaticRouteGateway       IpAddress,
    tchRgIpMgmtStaticRouteRipAdvertise  TruthValue
    }

tchRgIpMgmtStaticRouteIndex OBJECT-TYPE
    SYNTAX      INTEGER (1..16)
    MAX-ACCESS  not-accessible
    STATUS      current
    DESCRIPTION
        "The index of the the table."
    ::= { tchRgIpMgmtStaticRouteEntry 1 }

tchRgIpMgmtStaticRouteRowStatus OBJECT-TYPE
    SYNTAX      RowStatus
    MAX-ACCESS  read-create
    STATUS      current
    DESCRIPTION
        "The row status."
    ::= { tchRgIpMgmtStaticRouteEntry 2 }

tchRgIpMgmtStaticRouteNetwork OBJECT-TYPE
    SYNTAX      IpAddress
    MAX-ACCESS  read-write
    STATUS      current
    DESCRIPTION
        "Static route IP network definition"
    ::= { tchRgIpMgmtStaticRouteEntry 3 }

tchRgIpMgmtStaticRouteSubnetMask OBJECT-TYPE
    SYNTAX      IpAddress
    MAX-ACCESS  read-write
    STATUS      current
    DESCRIPTION
        "Static route network mask definition"
    ::= { tchRgIpMgmtStaticRouteEntry 4 }

tchRgIpMgmtStaticRouteGateway OBJECT-TYPE
    SYNTAX      IpAddress
    MAX-ACCESS  read-write
    STATUS      current
    DESCRIPTION
        "Gateway to the network defined in
         tchRgIpMgmtStaticRouteNetwork and
         tchRgIpMgmtStaticRouteSubnetMask."
    ::= { tchRgIpMgmtStaticRouteEntry 5 }

tchRgIpMgmtStaticRouteRipAdvertise OBJECT-TYPE
    SYNTAX      TruthValue
    MAX-ACCESS  read-write
    STATUS      current
    DESCRIPTION
        "If set to true(1), then static route entry
         will be advertised in RIP."
    DEFVAL { false }
    ::= { tchRgIpMgmtStaticRouteEntry 6 }

-- WAN interface

tchRgIpMgmtWanAddr OBJECT IDENTIFIER ::= { tchRgIpMgmt 9 }

tchRgIpMgmtWanAddrBase OBJECT IDENTIFIER ::= { tchRgIpMgmtWanAddr 1 }

tchRgIpMgmtWanMode OBJECT-TYPE
    SYNTAX INTEGER {
        dhcp(1),
        static(2),
        dualIp(3),
        private(4)
        }
    MAX-ACCESS    read-write
    STATUS        current
    DESCRIPTION
        "When dualIp(3) is selected, the second IP stack is used for
         user operations.
	 private(4) is used to provide a private IP for RIP
         Stored in non-vol, dhcp(1) after factory reset."
	DEFVAL { dhcp }
    ::= { tchRgIpMgmtWanAddrBase 1 }

tchRgIpMgmtWanMtu OBJECT-TYPE
    SYNTAX INTEGER (0..1500)
    UNITS       "bytes"
    MAX-ACCESS     read-write
    STATUS         current
    DESCRIPTION
        "MTU size for the IP layer. Valid range is 256 to 1500.
         0 is the default which is 1500.
         Stored in non-vol, 0 after factory reset."
    ::= { tchRgIpMgmtWanAddrBase 2 }

tchRgIpMgmtWanTtl OBJECT-TYPE
    SYNTAX INTEGER (0..255)
    UNITS       "hops"
    MAX-ACCESS     read-write
    STATUS         current
    DESCRIPTION
        "TTL for the IP packets forwarded to WAN.
         0 means no change to the original TTL (after
         being decreased by 1).
         Stored in non-vol, 0 after factory reset."
    ::= { tchRgIpMgmtWanAddrBase 3 }


tchRgIpMgmtWanAddrDynamic OBJECT IDENTIFIER ::= { tchRgIpMgmtWanAddr 2 }

tchRgIpMgmtWanAddrDynamicIp OBJECT-TYPE
    SYNTAX      IpAddress
    MAX-ACCESS  read-write
    STATUS      current
    DESCRIPTION
        "The IP address for the DHCP-assigned router address. This is the outside-facing WAN address of the router. Stored in non-vol, 0.0.0.0 after factory reset."
    ::= { tchRgIpMgmtWanAddrDynamic 1 }

tchRgIpMgmtWanAddrDynamicLeaseTime OBJECT-TYPE
    SYNTAX      Unsigned32
    UNITS       "seconds"
    MAX-ACCESS  read-write
    STATUS      current
    DESCRIPTION
            "The lease time for the dynamically assigned WAN address."
    DEFVAL { 3600 }
    ::= { tchRgIpMgmtWanAddrDynamic 2 }

    tchRgIpMgmtWanAddrDynamicGateway OBJECT-TYPE
    SYNTAX      IpAddress
    MAX-ACCESS  read-write
    STATUS      current
    DESCRIPTION
        "This is the WAN IP address of the gateway for the router. Stored in non-vol, 0.0.0.0 after factory reset."
    ::= { tchRgIpMgmtWanAddrDynamic 3 }

tchRgIpMgmtWanAddrStatic OBJECT IDENTIFIER ::= { tchRgIpMgmtWanAddr 3 }

tchRgIpMgmtWanStaticNetwork OBJECT-TYPE
    SYNTAX      IpAddress
    MAX-ACCESS  read-write
    STATUS      current
    DESCRIPTION
        "Stored in non-vol, 0.0.0.0 after factory reset."
    ::= { tchRgIpMgmtWanAddrStatic 1 }

tchRgIpMgmtWanStaticSubnetMask OBJECT-TYPE
    SYNTAX      IpAddress
    MAX-ACCESS  read-write
    STATUS      current
    DESCRIPTION
        "Stored in non-vol, 0.0.0.0 after factory reset."
    ::= { tchRgIpMgmtWanAddrStatic 2 }

tchRgIpMgmtWanStaticGateway OBJECT-TYPE
    SYNTAX      IpAddress
    MAX-ACCESS  read-write
    STATUS      current
    DESCRIPTION
        "Stored in non-vol, 0.0.0.0 after factory reset."
    ::= { tchRgIpMgmtWanAddrStatic 3 }

tchRgIpMgmtWanStaticNameServerEnable OBJECT-TYPE
    SYNTAX TruthValue
    MAX-ACCESS read-write
    STATUS current
    DESCRIPTION
        "Defines whether static WAN DNS is enabled."
    ::= { tchRgIpMgmtWanAddrStatic 4 }

tchRgIpMgmtWanStaticHostName OBJECT-TYPE
    SYNTAX      SnmpAdminString
    MAX-ACCESS  read-write
    STATUS      current
    DESCRIPTION
        "This is the static host name of WAN."
    ::= { tchRgIpMgmtWanAddrStatic 5 }

tchRgIpMgmtWanStaticDomainName OBJECT-TYPE
    SYNTAX      SnmpAdminString
    MAX-ACCESS  read-write
    STATUS      current
    DESCRIPTION
        "This is the static domain name of WAN."
    ::= { tchRgIpMgmtWanAddrStatic 6 }

tchRgIpMgmtWanAddrDualIp OBJECT IDENTIFIER ::= { tchRgIpMgmtWanAddr 4 }

tchRgIpMgmtWanDualIpAddr OBJECT-TYPE
    SYNTAX      IpAddress
    MAX-ACCESS  read-only
    STATUS      current
    DESCRIPTION
        "IP address for the second IP stack.
         If not specified and tchRgIpMgmtWanMode is set to
         dualIp(3), DHCP is used to acquire the IP address.
         Note: this object can only be set from config file."
    DEFVAL  { '00000000'h }
    ::= { tchRgIpMgmtWanAddrDualIp 1 }

tchRgIpMgmtWanDualIpRipAdvertised OBJECT-TYPE
    SYNTAX      TruthValue
    MAX-ACCESS  read-write
    STATUS      current
    DESCRIPTION
        "Specifies if the IP address is to be advertised in RIP,
         if RIP is enabled.
         Note: this object can only be set from config file."
    DEFVAL { true }
    ::= { tchRgIpMgmtWanAddrDualIp 2 }

tchRgIpMgmtWanAddrBackup OBJECT IDENTIFIER ::= { tchRgIpMgmtWanAddr 5 }

tchRgIpMgmtWanAddrBackupDefGw OBJECT-TYPE
    SYNTAX      IpAddress
    MAX-ACCESS  read-write
    STATUS      current
    DESCRIPTION
        "IP address for the default gateway that is used when the
         cable modem interface is offline. This object is not in
         effect when the cable modem is online.
         Note: this object is stored in non-vol and is 0.0.0.0
               after factory reset.
         The value of 0.0.0.0 means that this object is not in
         effect."
    ::= { tchRgIpMgmtWanAddrBackup 1 }



tchRgIpMgmtPassthrough OBJECT IDENTIFIER ::= { tchRgIpMgmt 10 }

tchRgIpMgmtPassthroughClientTable  OBJECT-TYPE
    SYNTAX      SEQUENCE OF TchRgIpMgmtPassthroughClientEntry
    MAX-ACCESS  not-accessible
    STATUS      current
    DESCRIPTION
        "A table of MAC addresses which represents stations that
         will be allowed to connect to the network bypassing any
         security, NAT and routing related settings. These
         stations are effectively behind bridged device."
    ::= { tchRgIpMgmtPassthrough 1 }

tchRgIpMgmtPassthroughClientEntry OBJECT-TYPE
    SYNTAX      TchRgIpMgmtPassthroughClientEntry
    MAX-ACCESS  not-accessible
    STATUS      current
    DESCRIPTION
        "A row in the table that specifies a single station MAC address."
    INDEX   { tchRgIpMgmtPassthroughClientIndex }
    ::= { tchRgIpMgmtPassthroughClientTable 1 }

TchRgIpMgmtPassthroughClientEntry ::=
    SEQUENCE    {
        tchRgIpMgmtPassthroughClientIndex       INTEGER,
        tchRgIpMgmtPassthroughClientRowStatus   RowStatus,
        tchRgIpMgmtPassthroughClientMacAddress  MacAddress
    }

tchRgIpMgmtPassthroughClientIndex OBJECT-TYPE
    SYNTAX      INTEGER (1..32)
    MAX-ACCESS  not-accessible
    STATUS      current
    DESCRIPTION
        "Indicates the instance of this table row."
    ::= { tchRgIpMgmtPassthroughClientEntry 1 }

tchRgIpMgmtPassthroughClientRowStatus OBJECT-TYPE
    SYNTAX      RowStatus
    MAX-ACCESS  read-write
    STATUS      current
    DESCRIPTION
        "The row status."
    ::= { tchRgIpMgmtPassthroughClientEntry 2 }

tchRgIpMgmtPassthroughClientMacAddress OBJECT-TYPE
    SYNTAX      MacAddress
    MAX-ACCESS  read-create
    STATUS      current
    DESCRIPTION
        "A MAC address of a station which will be allowed to connect
         directly to the network."
     ::= { tchRgIpMgmtPassthroughClientEntry 3 } 

tchRgIpMgmtPassthroughEnable OBJECT-TYPE
    SYNTAX      TruthValue
    MAX-ACCESS  read-write
    STATUS      current
    DESCRIPTION
        "True = Enable the IP Passthrough feature. False = disable.
        this Value is written to non-vol and set to false after a factory reset."
    DEFVAL { false }
    ::= { tchRgIpMgmtPassthrough 2 }



tchRgIpMgmtLanExtraSubnetTable OBJECT-TYPE
    SYNTAX SEQUENCE OF TchRgIpMgmtLanExtraSubnetEntry
    MAX-ACCESS not-accessible
    STATUS current
    DESCRIPTION
            "Additional IP addresses for primary LAN interface.
             If RIP is enabled, all subnets are advertised.
             All objects are stored in non-vol. The table
             is empty after factory reset."
    ::= { tchRgIpMgmt 11 }

tchRgIpMgmtLanExtraSubnetEntry OBJECT-TYPE
    SYNTAX      TchRgIpMgmtLanExtraSubnetEntry
    MAX-ACCESS  not-accessible
    STATUS     current
    DESCRIPTION
            "List of networks on the LAN side."
    INDEX { ifIndex }
    ::= { tchRgIpMgmtLanExtraSubnetTable 1 }

TchRgIpMgmtLanExtraSubnetEntry ::= SEQUENCE {
    tchRgIpMgmtLanExtraSubnetIndex      INTEGER,
    tchRgIpMgmtLanExtraSubnetRowStatus  RowStatus,
    tchRgIpMgmtLanExtraSubnetIpAddress  IpAddress,
    tchRgIpMgmtLanExtraSubnetSubnetMask IpAddress,
    tchRgIpMgmtLanExtraSubnetGateway    IpAddress
    }

tchRgIpMgmtLanExtraSubnetIndex OBJECT-TYPE
    SYNTAX INTEGER
        {
        secondSubnet(1),
        thirdSubnet(2),
        fourthSubnet(3)
        }
    MAX-ACCESS  not-accessible
    STATUS      current
    DESCRIPTION
        "Indicates the instance of this table row."
    ::= { tchRgIpMgmtLanExtraSubnetEntry 1 }

tchRgIpMgmtLanExtraSubnetRowStatus OBJECT-TYPE
    SYNTAX      RowStatus
    MAX-ACCESS  read-create
    STATUS      current
    DESCRIPTION
        "The row status."
    ::= { tchRgIpMgmtLanExtraSubnetEntry 2 }

tchRgIpMgmtLanExtraSubnetIpAddress OBJECT-TYPE
    SYNTAX      IpAddress
    MAX-ACCESS  read-write
    STATUS      current
    DESCRIPTION
            ""
    ::= { tchRgIpMgmtLanExtraSubnetEntry 3 }

tchRgIpMgmtLanExtraSubnetSubnetMask OBJECT-TYPE
    SYNTAX      IpAddress
    MAX-ACCESS  read-write
    STATUS      current
    DESCRIPTION
            ""
    DEFVAL { 'ffffff00'h }    -- 255.255.255.0
    ::= { tchRgIpMgmtLanExtraSubnetEntry 4 }

tchRgIpMgmtLanExtraSubnetGateway OBJECT-TYPE
    SYNTAX      IpAddress
    MAX-ACCESS  read-write
    STATUS      current
    DESCRIPTION
            ""
    ::= { tchRgIpMgmtLanExtraSubnetEntry 5 }

-- LT2P v2 settings

tchRgIpMgmtL2tpClientTable OBJECT-TYPE
    SYNTAX SEQUENCE OF TchRgIpMgmtL2tpClientEntry
    MAX-ACCESS not-accessible
    STATUS obsolete
    DESCRIPTION
            "L2TP settings for a BSS when tchRgIpMgmtLanMode
             is set to l2tp-client(3)."
    ::= { tchRgIpMgmt 12 }

tchRgIpMgmtL2tpClientEntry OBJECT-TYPE
    SYNTAX      TchRgIpMgmtL2tpClientEntry
    MAX-ACCESS  not-accessible
    STATUS     obsolete
    DESCRIPTION
            "The entry is available only when tchRgIpMgmtLanMode is
             set to l2tp-client(3) for the specific ifIndex."
    INDEX { ifIndex }
    ::= { tchRgIpMgmtL2tpClientTable 1 }

TchRgIpMgmtL2tpClientEntry ::= SEQUENCE {

    tchRgIpMgmtL2tpClientServer      IpAddress,
    tchRgIpMgmtL2tpClientPppUsername OCTET STRING,
    tchRgIpMgmtL2tpClientPppPassword OCTET STRING
    }

tchRgIpMgmtL2tpClientServer OBJECT-TYPE
    SYNTAX      IpAddress
    MAX-ACCESS  read-write
    STATUS      obsolete
    DESCRIPTION
            "IP address of the L2TP server."
    ::= { tchRgIpMgmtL2tpClientEntry 1 }

tchRgIpMgmtL2tpClientPppUsername OBJECT-TYPE
    SYNTAX      OCTET STRING (SIZE(0..32))
    MAX-ACCESS  read-write
    STATUS      obsolete
    DESCRIPTION
            ""
    ::= { tchRgIpMgmtL2tpClientEntry 2 }

tchRgIpMgmtL2tpClientPppPassword OBJECT-TYPE
    SYNTAX      OCTET STRING (SIZE(0..32))
    MAX-ACCESS  read-write
    STATUS      obsolete
    DESCRIPTION
            ""
    ::= { tchRgIpMgmtL2tpClientEntry 3 }

-- **********************
-- LAN PORT Control Table
-- **********************
tchRgIpMgmtLanPortControl   OBJECT IDENTIFIER ::=  { tchRgIpMgmt 13 }


tchRgIpMgmtLanPortControlTable OBJECT-TYPE
       SYNTAX      SEQUENCE OF TchRgIpMgmtLanPortControlEntry
       MAX-ACCESS  not-accessible
       STATUS      current
       DESCRIPTION
               "Table to control the mode for each LAN PORT.
               LAN PORTs are numbered 1-4 and are mapped to physical
               port location. Each port can either be in router or
               in bridge mode."
    ::= { tchRgIpMgmtLanPortControl 1 }

tchRgIpMgmtLanPortControlEntry OBJECT-TYPE
    SYNTAX      TchRgIpMgmtLanPortControlEntry
    MAX-ACCESS  not-accessible
    STATUS      current
    DESCRIPTION
            ""
    INDEX { tchRgIpMgmtLanPortControlIndex }
    ::= { tchRgIpMgmtLanPortControlTable 1 }

TchRgIpMgmtLanPortControlEntry ::= SEQUENCE {
    tchRgIpMgmtLanPortControlIndex       INTEGER,
    tchRgIpMgmtLanPortMode               INTEGER
    }

tchRgIpMgmtLanPortControlIndex OBJECT-TYPE
    SYNTAX      INTEGER (1..4)
    MAX-ACCESS  not-accessible
    STATUS      current
    DESCRIPTION
            "The index for each LAN port"
    ::= { tchRgIpMgmtLanPortControlEntry 1 }

tchRgIpMgmtLanPortMode OBJECT-TYPE
    SYNTAX  INTEGER {
            bridge (1),
            router (2)
            }
    MAX-ACCESS  read-write
    STATUS      current
    DESCRIPTION
            "Each physical LAN port can either be controlled
            as bridge or router. The tchRgIpMgmtLanPortMode MIB only works
            when TchRgIpMgmtLanMode.32=4(Mixed). Setting this MIB
            through SNMP will take effect only after
            tchRgIpMgmtApplySettings.0 set to true and this setting will
            reboot to take effect"
    ::= { tchRgIpMgmtLanPortControlEntry 2 }

tchRgIpMgmtRestoreDefaults OBJECT-TYPE
   SYNTAX INTEGER {
                        disable(0),
                        bridgeDefaults(1),
                        routerDefaults(2)
                        }
   MAX-ACCESS read-write
   STATUS current
   DESCRIPTION
                "MIB to control the default behavior for LAN mode.
                NOTE: This is customer specific ONLY. Not available in GA yet
                Default behavior is disabled (0). - This means that GA behavior is the normal behavior.
                bridgeDefaults(1) - All the MIB objects in bridgeDefaults group would be set when CM boots up and would be retained across reboots/factory reset
                routerDefaults(2) - All the MIB objects in routerDefaults group would be set when CM boots up and would be retained across reboots/factory reset"
  DEFVAL { 0 }

  ::= { tchRgIpMgmt 14 }

--====================================================================
--
--    tchRgIpMgmtLanAddrIpv6Table (CDP Ipv6 Address Table)
--
--    The tchRgIpMgmtLanAddrUpv6Table contains the Ipv6 parameters
--   
--
--=========================================================================

tchRgIpMgmtLanAddrIpv6Table OBJECT-TYPE
       SYNTAX      SEQUENCE OF TchRgIpMgmtLanAddrIpv6Entry
       MAX-ACCESS  not-accessible
       STATUS      current
       DESCRIPTION
               "IP addresses of devices served by DHCPv6/SLAAC"
    ::= { tchRgIpMgmt 15 }

tchRgIpMgmtLanAddrIpv6Entry OBJECT-TYPE
    SYNTAX      TchRgIpMgmtLanAddrIpv6Entry
    MAX-ACCESS  not-accessible
    STATUS      current
    DESCRIPTION
            "List of general parameters pertaining to LAN-Trans IP
            address reservations and leases."
    INDEX { ifIndex, tchRgIpMgmtLanAddrIpv6Index }
    ::= { tchRgIpMgmtLanAddrIpv6Table 1 }

TchRgIpMgmtLanAddrIpv6Entry ::= SEQUENCE {
    tchRgIpMgmtLanAddrIpv6Index              INTEGER,
    tchRgIpMgmtLanAddrIpv6Ip                 InetAddress,
    tchRgIpMgmtLanAddrIpv6PhysAddr           PhysAddress,
    tchRgIpMgmtLanAddrIpv6Status             SnmpAdminString,
    tchRgIpMgmtLanAddrIpv6Method             SnmpAdminString,
    tchRgIpMgmtLanAddrIpv6ClientId           SnmpAdminString,
    tchRgIpMgmtLanAddrIpv6Interface          SnmpAdminString,
    tchRgIpMgmtLanAddrIpv6CpeStatus          INTEGER
    }

tchRgIpMgmtLanAddrIpv6Index OBJECT-TYPE
    SYNTAX      INTEGER (0..255)
    MAX-ACCESS  not-accessible
    STATUS      current
    DESCRIPTION
            "The index of the the LAN IPv6 Device in the LAN-Trans Realm."
    ::= { tchRgIpMgmtLanAddrIpv6Entry 1 }

tchRgIpMgmtLanAddrIpv6Ip OBJECT-TYPE
    SYNTAX      InetAddress
    MAX-ACCESS  read-only
    STATUS      current
    DESCRIPTION
            ""
    ::= { tchRgIpMgmtLanAddrIpv6Entry 3 }

tchRgIpMgmtLanAddrIpv6PhysAddr OBJECT-TYPE
    SYNTAX      PhysAddress
    MAX-ACCESS  read-only
    STATUS      current
    DESCRIPTION
            "The client's (i.e., LAN IP Device's) hardware address as
            indicated in the chaddr field of its DHCP REQUEST message."
    ::= { tchRgIpMgmtLanAddrIpv6Entry 4 }

tchRgIpMgmtLanAddrIpv6Status OBJECT-TYPE
    SYNTAX      SnmpAdminString
    MAX-ACCESS  read-only
    STATUS      current
    DESCRIPTION
            "Ipv6 Reachability state the device."
    ::= { tchRgIpMgmtLanAddrIpv6Entry 5 }

tchRgIpMgmtLanAddrIpv6Method OBJECT-TYPE
    SYNTAX      SnmpAdminString
    MAX-ACCESS  read-only
    STATUS      current
    DESCRIPTION
            "This is the method how IPv6 address was obtained SLAAC or DHCPv6."
    ::= { tchRgIpMgmtLanAddrIpv6Entry 6 }

tchRgIpMgmtLanAddrIpv6ClientId OBJECT-TYPE
    SYNTAX      SnmpAdminString
    MAX-ACCESS  read-only
    STATUS      current
    DESCRIPTION
            "This is the Client Class Identifier, based on DHCP option 60."
    ::= { tchRgIpMgmtLanAddrIpv6Entry 7 }

tchRgIpMgmtLanAddrIpv6Interface OBJECT-TYPE
    SYNTAX      SnmpAdminString
    MAX-ACCESS  read-only
    STATUS      current
    DESCRIPTION
            "This will show the associated interface (LAN, WiFi or MoCA) of the connected CPE."
    ::= { tchRgIpMgmtLanAddrIpv6Entry 8 }

tchRgIpMgmtLanAddrIpv6CpeStatus OBJECT-TYPE
    SYNTAX INTEGER {
        offline(0),
        online(1)
        }
    MAX-ACCESS    read-only
    STATUS        current
    DESCRIPTION
        "This MIB shows the client's current online status.
                - 0 - The client currently has no connectivity.
                - 1 - The client currently has connectivity and is online.
                "
    DEFVAL { 0 }
    ::= { tchRgIpMgmtLanAddrIpv6Entry 9 }


--============================================================================
--
--    tchRgIpMgmtConnectedDevices 
--
--    The table contains a summary of devices connected over various interfaces
--   
--
--=============================================================================
                                                                                
tchRgIpMgmtConnectedDevices   OBJECT IDENTIFIER ::=  { tchRgIpMgmt 16 }
                                                                                
                                                                                
tchRgIpMgmtConnectedDevicesSummary  OBJECT IDENTIFIER ::= { tchRgIpMgmtConnectedDevices 1 }    

tchRgIpMgmtTotalClientsOverMoCA OBJECT-TYPE      
    SYNTAX        INTEGER
    MAX-ACCESS    read-only
    STATUS        current
    DESCRIPTION
        "This MIB provides total number of devices that are connected over MoCA and have received IP address from
        gateway's DHCP pool"
    ::= { tchRgIpMgmtConnectedDevicesSummary 1 }
                                                                              
-- ====================================================
-- IPv6 Client MIBs
-- ====================================================
tchRgIPv6ClientPD OBJECT IDENTIFIER ::=  { tchRgIpMgmt  17 }


tchRgIPv6PDSize OBJECT-TYPE
    SYNTAX      Unsigned32 
    MAX-ACCESS  read-write
    STATUS      current
	DESCRIPTION
	    "PD length size request from client to CMTS, Allowed size 56 to 64"
	 DEFVAL { 62 }	
	::= { tchRgIPv6ClientPD 1 }		

tchRgRapidCommitEnable OBJECT-TYPE
    SYNTAX      TruthValue
    MAX-ACCESS  read-write
    STATUS      current
               DESCRIPTION
                   "Enables/Disables the Rapid-Commit in DHCPv6.
                              If true(1), Rapid-Commit is Enabled -> DHCP client obtain configuration parameters from the server through a rapid two message exchange (solicit and reply).
                              If false(2), Rapid-Commit is Disabled -> cDHCP client obtain configuration parameters from the server through a default 4 message exchange"
               DEFVAL { false }
    ::= { tchRgIPv6ClientPD 2 } 
	
-- Apply setting to activate chagnes:
tchRgIpMgmtApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until tchRgIpMgmtApplySettings is set to true or CM resets.
         Note: this applies only to the MIB objects that are stored
         in non-vol.
         Always returns false(2) when read."
    ::= { tchRgIpMgmt 1001 }


--====================================================================
--
--    tchRgIpMgmtLanAddrIpv6Dhcp branch
--
--    The tchRgIpMgmtLanAddrIpv6Dhcp
--
--
--=========================================================================

tchRgIpMgmtLanAddrIpv6Dhcp   OBJECT IDENTIFIER ::=  { tchRgIpMgmt 18 }




tchRgIpMgmtLanAddrIpv6DhcpLeaseTime OBJECT-TYPE
    SYNTAX      INTEGER
    MAX-ACCESS  read-write
    STATUS      current
    DESCRIPTION
            "Lease time applied by IPv6 DHCP server for LAN clients."
    ::= { tchRgIpMgmtLanAddrIpv6Dhcp 1 }

-- =============================================
-- EDNS0
--
-- Extension mechanisms for DNS 
-- =============================================	
	
	
tchRgIpMgmtEdns0Enable OBJECT-TYPE
    SYNTAX      TruthValue
    MAX-ACCESS  read-write
    STATUS      current
    DESCRIPTION      
        "MIB to control the eDNS0 activation state. Default behavior is disabled (0).
        If set to true(1), eDNS0 feature is enabled
        NOTE: VFG will continue to use tchRgIpMgmtEdns0Enable.  All other products will use tchRgEdns0Enable"
    ::= { tchRgIpMgmt 19 }

-- =============================================
-- FIREWALL
--
-- Also includes port tiggering, forwarding, DMZ
-- =============================================

tchRgFirewall OBJECT IDENTIFIER ::=  { tchRg 4 }

tchRgFirewallBase OBJECT IDENTIFIER ::=  { tchRgFirewall 1 }

tchRgFirewallProtection OBJECT-TYPE
SYNTAX INTEGER {
disable(0),
low(1),
medium (2),
high (3),
custom (4)
}
MAX-ACCESS read-write
STATUS current
DESCRIPTION
"Controls the firewall. This parameter is stored in non-vol and
is enabled after factory reset.
Disable: Completely disables the SPI Firewall
Low/ Enable: Is Equivalent to Old Firewall Enable Mode with No Ports Restricted
Medium: Enables the SPI Firewall plus includes a list of Allowed Services that will be allowed to through the Firewall
High: Enables the SPI Firewall plus a shortened list of Allowed Services
Custom: Enables the SPI Firewall set to custom values. For use with Puma-based products."
::= { tchRgFirewallBase 1 }

tchRgFirewallDmzAddress OBJECT-TYPE
    SYNTAX      IpAddress
    MAX-ACCESS  read-write
    STATUS      current
    DESCRIPTION
            "Stored in non-vol, 0.0.0.0 after facroty reset."
    ::= { tchRgFirewallBase 2 }

tchRgFirewallPortForwardEnable OBJECT-TYPE
    SYNTAX      TruthValue
    MAX-ACCESS  read-write
    STATUS      current
    DESCRIPTION
        "Enables or disables firewall port forwarding on the device."
    DEFVAL { false }
    ::= { tchRgFirewallBase 3 }

tchRgFirewallPortTriggerEnable OBJECT-TYPE
    SYNTAX      TruthValue
    MAX-ACCESS  read-write
    STATUS      current
    DESCRIPTION
        "Enables or disables firewall port triggering on the device."
    DEFVAL { false }
    ::= { tchRgFirewallBase 4 }

        tchRgFirewallTraffic OBJECT IDENTIFIER ::=  { tchRgFirewall 2 }

tchRgFirewallTrafficBlock OBJECT-TYPE
    SYNTAX BITS {
        proxy(0),
        cookies(1),
        javaApplets(2),
        activeX(3),
        popUp(4),
        fragmentedIp(5)
    }
    MAX-ACCESS    read-write
    STATUS        current
    DESCRIPTION
        "Controls blocking of certain traffic.
         Stored in non-vol, 0x00 after factory reset.
        Note: For DOCSIS 3.0 products with 553 and newer SW,
        proxy(0), cookies(1), javaApplets(2), activeX(3), popUp(4) are NOT Supported."
    ::= { tchRgFirewallTraffic 1 }

tchRgFirewallTrafficDetect OBJECT-TYPE
    SYNTAX BITS {
        portScan(0),
        ipFlood(1)
    }
    MAX-ACCESS    read-write
    STATUS        current
    DESCRIPTION
        "Controls detecting of certain traffic.
         Stored in non-vol, 0x40 after factory reset."
    ::= { tchRgFirewallTraffic 2 }

tchRgFirewallTrafficPassThru OBJECT-TYPE
    SYNTAX BITS {
        ipsec(0),
---     ipsec  defaulted to true. RO.
        pptp(1),
---     pptp  defaulted to true. RO.
        multicast(2),
        ident(3),
        icmp(4),
        ftpAlg(5),
        tftpAlg(6),
        kerb88Alg(7),
        netbiosAlg(8),
        ikeAlg(9),
        rtspAlg(10),
        kerb1293Alg(11),
        h225Alg(12),
        msnAlg(13),
        rsvpAlg(14),
        icqAlg(15),
        icqtalkAlg(16),
        irc666xAlg(17),
        net2phoneAlg(18),
        irc7000Alg(19),
        irc8000Alg(20),
        h323Alg(21),
        l2tpAlg(22),
---     l2tpAlg defaulted to true. RO.
        pptpAlg(23),
---     pptpAlg defaulted to true. RO.
        ipsecAlg(24)
---     ipSecAlg defaulted to true. RO.
    }
    MAX-ACCESS    read-write
    STATUS        current
    DESCRIPTION
        "Controls passthru for certain traffic:
                ipsec(0), Block IPSec
                pptp(1), Block PPTP
                multicast(2), Block Multicast
                ident(3), Block IDENT (port 113), for use with Puma-based products
                icmp(4), Block ICMP, for use with Puma-based products
                Stored in non-vol, 0xe0 after factory reset.
                To stay consistent with the behavior of this mib, Algs will be implemented 
                where 0 in the respective bit enables the Alg and a 1 disabled the Alg.
                Default value for ipsec, pptp, l2tpAlg, pptpAlg, and ipsecAlg is true. 
                These bits can no longer be controlled via mib. They are always enabled."
    ::= { tchRgFirewallTraffic 3 }

tchRgFirewallWANBlockingEnable OBJECT-TYPE
    SYNTAX TruthValue
    MAX-ACCESS  read-write
    STATUS      current
    DESCRIPTION
        "Controls WAN blocking RG feature.
         Stored in non-vol, enabled after factory reset."
    ::= { tchRgFirewallTraffic 4 }

tchRgFirewallIpv6Protection OBJECT-TYPE
    SYNTAX INTEGER {
        disable(0),
        enableLow(1), 
        medium(2),
        high(3),
        custom(4)
    }
    MAX-ACCESS read-write
    STATUS current
    DESCRIPTION
      "Controls the IPv6 firewall. This parameter is stored in non-vol and
       is enabled after factory reset.
       Disable: Completely disables the SPI Firewall
       Low/ Enable: Is Equivalent to Old Firewall Enable Mode with No Ports Restricted
       Medium: Enables the SPI Firewall plus includes a list of Allowed Services that will be allowed to through the Firewall
       High: Enables the SPI Firewall plus a shortened list of Allowed Services
       Custom: Enables the SPI Firewall set to custom values. For use with Puma-based products."

    DEFVAL { 1 }
    ::= { tchRgFirewallBase 5 }


tchRgFirewalIPortScanDetection OBJECT-TYPE
    SYNTAX  INTEGER {
            false  (0),
            true   (1)
    }
      MAX-ACCESS    read-write
      STATUS        current
      DESCRIPTION
        "The default value is false(0).
         If read or set false, then no PortScan detection is configured
         If read or set  true(1), then at PortScan detection is configured. "
      
      ::= { tchRgFirewallBase 6}  

tchRgFirewallIPFloodDetection OBJECT-TYPE
    SYNTAX  INTEGER {
            false  (0),
            true   (1)
    }
      MAX-ACCESS    read-write
      STATUS        current
      DESCRIPTION
        "The default value is false(0).
         If read orset false (0), then no IPFloodDetection is configured
         If read or set  true (1), then IPFloodDetection is configured. "
      
      ::= { tchRgFirewallBase 7}  

tchRgFirewallPortFwdStatus OBJECT-TYPE
    SYNTAX  INTEGER {
            false  (0),
            true   (1)
    }
      MAX-ACCESS    read-only
      STATUS        current
      DESCRIPTION
        "The default value is false(0).
         If read false, then no port forwarding is configured
         If read true (!=0), then at least one port forwarding rule is configured. returns in fact the number of forwarding ports activated"
      
      ::= { tchRgFirewallBase 8}  

-- Firewall events reporting

tchRgFirewallReport OBJECT IDENTIFIER ::=  { tchRgFirewall 4 }

tchRgFirewallReportEventTable OBJECT-TYPE
       SYNTAX      SEQUENCE OF TchRgFirewallReportEventEntry
       MAX-ACCESS  not-accessible
       STATUS      current
       DESCRIPTION
               "This table is stored in non-vol and is empty
                after factory reset."
    ::= { tchRgFirewallReport 1 }

tchRgFirewallReportEventEntry OBJECT-TYPE
    SYNTAX      TchRgFirewallReportEventEntry
    MAX-ACCESS  not-accessible
    STATUS      current
    DESCRIPTION
            ""
    INDEX { tchRgFirewallReportEventIndex }
    ::= { tchRgFirewallReportEventTable 1 }

TchRgFirewallReportEventEntry ::= SEQUENCE {
    tchRgFirewallReportEventIndex          INTEGER,
    tchRgFirewallReportEventDescription    SnmpAdminString,
    tchRgFirewallReportEventCount          INTEGER,
    tchRgFirewallReportEventLastOccurance  SnmpAdminString,
    tchRgFirewallReportEventTarget         SnmpAdminString,
    tchRgFirewallReportEventSource         SnmpAdminString
    }

tchRgFirewallReportEventIndex OBJECT-TYPE
    SYNTAX      INTEGER (0..32)
    MAX-ACCESS  not-accessible
    STATUS      current
    DESCRIPTION
            "The index"
    ::= { tchRgFirewallReportEventEntry 1 }

tchRgFirewallReportEventDescription OBJECT-TYPE
    SYNTAX      SnmpAdminString
    MAX-ACCESS  read-only
    STATUS      current
    DESCRIPTION
            ""
    ::= { tchRgFirewallReportEventEntry 2 }

tchRgFirewallReportEventCount OBJECT-TYPE
    SYNTAX      INTEGER
    MAX-ACCESS  read-only
    STATUS      current
    DESCRIPTION
            ""
    ::= { tchRgFirewallReportEventEntry 3 }

tchRgFirewallReportEventLastOccurance OBJECT-TYPE
    SYNTAX      SnmpAdminString
    MAX-ACCESS  read-only
    STATUS      current
    DESCRIPTION
            ""
    ::= { tchRgFirewallReportEventEntry 4 }

tchRgFirewallReportEventTarget OBJECT-TYPE
    SYNTAX      SnmpAdminString
    MAX-ACCESS  read-only
    STATUS      current
    DESCRIPTION
            ""
    ::= { tchRgFirewallReportEventEntry 5 }

tchRgFirewallReportEventSource OBJECT-TYPE
    SYNTAX      SnmpAdminString
    MAX-ACCESS  read-only
    STATUS      current
    DESCRIPTION
            ""
    ::= { tchRgFirewallReportEventEntry 6 }


tchRgFirewallReportMgmt OBJECT IDENTIFIER ::=  { tchRgFirewallReport 2 }

tchRgFirewallReportMgmtClearLog OBJECT-TYPE
    SYNTAX TruthValue
    MAX-ACCESS    read-write
    STATUS        current
    DESCRIPTION
        "Note: this object does not need tchRgFirewallApplySettings
         to take effect."
    DEFVAL { false }
    ::= { tchRgFirewallReportMgmt 1 }

tchRgFirewallReportEmailLogNow OBJECT-TYPE
    SYNTAX TruthValue
    MAX-ACCESS    read-write
    STATUS        current
    DESCRIPTION
        "Triggers sending currect logs via email. Always returns false.
         Note: this objects does not need tchRgFirewallApplySettings to
         send the logs."
    DEFVAL { false }
    ::= { tchRgFirewallReportMgmt 2 }


tchRgFirewallReportEmail OBJECT IDENTIFIER ::=  { tchRgFirewallReport 3 }

tchRgFirewallReportEmailEnable OBJECT-TYPE
    SYNTAX TruthValue
    MAX-ACCESS    read-write
    STATUS        current
    DESCRIPTION
        "Enables sending logs via email. Email is sent when an event happens."
    ::= { tchRgFirewallReportEmail 1 }

tchRgFirewallReportEmailAddress OBJECT-TYPE
    SYNTAX SnmpAdminString
    MAX-ACCESS    read-write
    STATUS        current
    DESCRIPTION
        "This is stored in non-vol and is empty after factory reset."
    ::= { tchRgFirewallReportEmail 2 }

tchRgFirewallReportEmailSmtpServer OBJECT-TYPE
    SYNTAX SnmpAdminString
    MAX-ACCESS    read-write
    STATUS        current
    DESCRIPTION
        "IP address or FQDN.
         Stored in non-vol. Empty after factory reset."
    ::= { tchRgFirewallReportEmail 3 }

tchRgFirewallReportEmailUsername OBJECT-TYPE
    SYNTAX SnmpAdminString
    MAX-ACCESS    read-write
    STATUS        current
    DESCRIPTION
        "This is stored in non-vol and is empty after factory reset."
    ::= { tchRgFirewallReportEmail 4 }

tchRgFirewallReportEmailPassword OBJECT-TYPE
    SYNTAX SnmpAdminString
    MAX-ACCESS    read-write
    STATUS        current
    DESCRIPTION
        "This is stored in non-vol and is empty after factory reset."
    ::= { tchRgFirewallReportEmail 5 }


-- Firewall IP filtering

tchRgFirewallRules OBJECT IDENTIFIER ::=  { tchRgFirewall 5 }

tchRgFirewallIpFilterTable OBJECT-TYPE
       SYNTAX      SEQUENCE OF TchRgFirewallIpFilterEntry
       MAX-ACCESS  not-accessible
       STATUS      current
       DESCRIPTION
               "This table is stored in non-vol and is empty
                after factory reset."
    ::= { tchRgFirewallRules 1 }

tchRgFirewallIpFilterEntry OBJECT-TYPE
    SYNTAX      TchRgFirewallIpFilterEntry
    MAX-ACCESS  not-accessible
    STATUS      current
    DESCRIPTION
            ""
    INDEX { tchRgFirewallIpFilterIndex }
    ::= { tchRgFirewallIpFilterTable 1 }

TchRgFirewallIpFilterEntry ::= SEQUENCE {
    tchRgFirewallIpFilterIndex              INTEGER,
    tchRgFirewallIpFilterRowStatus          RowStatus,
    tchRgFirewallIpFilterAddressStart       IpAddress,
    tchRgFirewallIpFilterAddressEnd         IpAddress,
    tchRgFirewallIpFilterTrusted            INTEGER,
    tchRgFirewallIpFilterPolicy             INTEGER
    }

tchRgFirewallIpFilterIndex OBJECT-TYPE
    SYNTAX      INTEGER (1..10)
    MAX-ACCESS  not-accessible
    STATUS      current
    DESCRIPTION
            "The index"
    ::= { tchRgFirewallIpFilterEntry 1 }

tchRgFirewallIpFilterRowStatus OBJECT-TYPE
    SYNTAX      RowStatus
    MAX-ACCESS  read-create
    STATUS      current
    DESCRIPTION
            "The row status. A row can be destroyed.
             If the row is not used, set to notInService."
    ::= { tchRgFirewallIpFilterEntry 2 }

tchRgFirewallIpFilterAddressStart OBJECT-TYPE
    SYNTAX      IpAddress
    MAX-ACCESS  read-write
    STATUS      current
    DESCRIPTION
            ""
    ::= { tchRgFirewallIpFilterEntry 3 }

tchRgFirewallIpFilterAddressEnd OBJECT-TYPE
    SYNTAX      IpAddress
    MAX-ACCESS  read-write
    STATUS      current
    DESCRIPTION
            ""
    ::= { tchRgFirewallIpFilterEntry 4 }

tchRgFirewallIpFilterTrusted OBJECT-TYPE
    SYNTAX      INTEGER {
        block(1),
        permit(2)
    }
    MAX-ACCESS  read-write
    STATUS      current
    DESCRIPTION
            "Block/Permit this IP address based on tchRgFirewallIpFilterPolicy"
    DEFVAL { block }
    ::= { tchRgFirewallIpFilterEntry 5 }

tchRgFirewallIpFilterPolicy OBJECT-TYPE
    SYNTAX      INTEGER {
        urlkeyword(1),
        port(2),
                none(3)
    }
    MAX-ACCESS  read-write
    STATUS      current
    DESCRIPTION
            "If urlkeyword(1), tchRgFirewallIpFilterTrusted can be set to permit a particular computer regardless of tchRgFirewallUrlKeywordFilterTable rules
            If port(2), tchRgFirewallIpFilterTrusted can be set to permit a particular computer regardless of tchRgFirewallPortFilterTable rules
                If none(3), tchRgFirewallIpFilterTrusted can be set to block or permit a computer regardless of any existing rules"
    DEFVAL { none }
    ::= { tchRgFirewallIpFilterEntry 6 }

tchRgFirewallPortFilterTable OBJECT-TYPE
       SYNTAX      SEQUENCE OF TchRgFirewallPortFilterEntry
       MAX-ACCESS  not-accessible
       STATUS      current
       DESCRIPTION
               "This table is stored in non-vol and is empty
                after factory reset."
    ::= { tchRgFirewallRules 2 }

tchRgFirewallPortFilterEntry OBJECT-TYPE
    SYNTAX      TchRgFirewallPortFilterEntry
    MAX-ACCESS  not-accessible
    STATUS      current
    DESCRIPTION
            ""
    INDEX { tchRgFirewallPortFilterIndex }
    ::= { tchRgFirewallPortFilterTable 1 }

TchRgFirewallPortFilterEntry ::= SEQUENCE {
    tchRgFirewallPortFilterIndex              INTEGER,
    tchRgFirewallPortFilterRowStatus          RowStatus,
    tchRgFirewallPortFilterPortStart          InetPortNumber,
    tchRgFirewallPortFilterPortEnd            InetPortNumber,
    tchRgFirewallPortFilterProto              INTEGER,
    tchRgFirewallPortFilterAlwaysBlock        TruthValue,
    tchRgFirewallPortFilterBlockStartTime     OCTET STRING,
    tchRgFirewallPortFilterBlockEndTime       OCTET STRING,
    tchRgFirewallPortFilterBlockDays          BITS
    }

tchRgFirewallPortFilterIndex OBJECT-TYPE
    SYNTAX      INTEGER (1..10)
    MAX-ACCESS  not-accessible
    STATUS      current
    DESCRIPTION
            "The index"
    ::= { tchRgFirewallPortFilterEntry 1 }

tchRgFirewallPortFilterRowStatus OBJECT-TYPE
    SYNTAX      RowStatus
    MAX-ACCESS  read-create
    STATUS      current
    DESCRIPTION
            "The row status. A row can be destroyed.
             If the row is not used, set to notInService."
    ::= { tchRgFirewallPortFilterEntry 2 }

tchRgFirewallPortFilterPortStart OBJECT-TYPE
    SYNTAX      InetPortNumber
    MAX-ACCESS  read-write
    STATUS      current
    DESCRIPTION
            ""
    ::= { tchRgFirewallPortFilterEntry 5 }

tchRgFirewallPortFilterPortEnd OBJECT-TYPE
    SYNTAX      InetPortNumber
    MAX-ACCESS  read-write
    STATUS      current
    DESCRIPTION
            ""
    ::= { tchRgFirewallPortFilterEntry 6 }

tchRgFirewallPortFilterProto OBJECT-TYPE
    SYNTAX  INTEGER {
        udp(1),
        tcp(2),
        udpTcp(3)
        }
    MAX-ACCESS  read-write
    STATUS      current
    DESCRIPTION
            "IP protocol to block."
    DEFVAL { 3 }
    ::= { tchRgFirewallPortFilterEntry 7 }

tchRgFirewallPortFilterAlwaysBlock OBJECT-TYPE
    SYNTAX      TruthValue
    MAX-ACCESS  read-write
    STATUS      current
    DESCRIPTION
        "If True(1), always be blocked, regardless of startTime, endTime and blockDays
        If False(2), blocked at time set in startTime, endTime and blockDays"
    DEFVAL { true }
    ::= { tchRgFirewallPortFilterEntry 8 }

tchRgFirewallPortFilterBlockStartTime OBJECT-TYPE
    SYNTAX      OCTET STRING (SIZE (5))
    MAX-ACCESS  read-write
    STATUS      current
    DESCRIPTION
        "24 Hour format HH:MM to set the start time to block"
    ::= { tchRgFirewallPortFilterEntry 9 }

tchRgFirewallPortFilterBlockEndTime OBJECT-TYPE
    SYNTAX      OCTET STRING (SIZE (5))
    MAX-ACCESS  read-write
    STATUS      current
    DESCRIPTION
        "24 Hour format HH:MM to set the end time to block"
    ::= { tchRgFirewallPortFilterEntry 10 }

tchRgFirewallPortFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block"
    ::= { tchRgFirewallPortFilterEntry 11 }
tchRgFirewallMacFilterTable  OBJECT-TYPE
    SYNTAX      SEQUENCE OF TchRgFirewallMacFilterEntry
    MAX-ACCESS  not-accessible
    STATUS      current
    DESCRIPTION
        "A table of clients MAC addresses that are denied from accessing Internet."
    ::= { tchRgFirewallRules 3 }

tchRgFirewallMacFilterEntry OBJECT-TYPE
    SYNTAX      TchRgFirewallMacFilterEntry
    MAX-ACCESS  not-accessible
    STATUS      current
    DESCRIPTION
        "A row in the table that specifies a single station MAC address."
    INDEX   { tchRgFirewallMacFilterIndex }
    ::= { tchRgFirewallMacFilterTable 1 }

TchRgFirewallMacFilterEntry ::=
    SEQUENCE    {
            tchRgFirewallMacFilterIndex              INTEGER,
            tchRgFirewallMacFilterRowStatus          RowStatus,
            tchRgFirewallMacFilterAddress          MacAddress,
            tchRgFirewallMacFilterAlwaysBlock      TruthValue,
            tchRgFirewallMacFilterBlockStartTime   OCTET STRING,
            tchRgFirewallMacFilterBlockEndTime     OCTET STRING,
            tchRgFirewallMacFilterBlockDays        BITS
    }

tchRgFirewallMacFilterIndex OBJECT-TYPE
    SYNTAX      INTEGER (1..20)
    MAX-ACCESS  not-accessible
    STATUS      current
    DESCRIPTION
            "The index"
    ::= { tchRgFirewallMacFilterEntry 1 }

tchRgFirewallMacFilterRowStatus OBJECT-TYPE
    SYNTAX      RowStatus
    MAX-ACCESS  read-create
    STATUS      current
    DESCRIPTION
            "The row status. A row can be destroyed.
             If the row is not used, set to notInService."
    ::= { tchRgFirewallMacFilterEntry 2 }

tchRgFirewallMacFilterAddress OBJECT-TYPE
    SYNTAX      MacAddress
    MAX-ACCESS  read-write
    STATUS      current
    DESCRIPTION
        "A MAC address of a station that cannot access Internet."
    ::= { tchRgFirewallMacFilterEntry 3 }

tchRgFirewallMacFilterAlwaysBlock OBJECT-TYPE
    SYNTAX      TruthValue
    MAX-ACCESS  read-write
    STATUS      current
    DESCRIPTION
        "If true(1), always be blocked/permitted, regardless of startTime, endTime and blockDays
        If false(2), blocked/permitted at time set in startTime, endTime and blockDays"
    DEFVAL { true }
    ::= { tchRgFirewallMacFilterEntry 4 }

tchRgFirewallMacFilterBlockStartTime OBJECT-TYPE
    SYNTAX      OCTET STRING (SIZE (5))
    MAX-ACCESS  read-write
    STATUS      current
    DESCRIPTION
        "24 Hour format HH:MM to set the start time to block/permit"
    ::= { tchRgFirewallMacFilterEntry 5 }

tchRgFirewallMacFilterBlockEndTime OBJECT-TYPE
    SYNTAX      OCTET STRING (SIZE (5))
    MAX-ACCESS  read-write
    STATUS      current
    DESCRIPTION
        "24 Hour format HH:MM to set the end time to block/permit"
    ::= { tchRgFirewallMacFilterEntry 6 }

tchRgFirewallMacFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block/permit"
    ::= { tchRgFirewallMacFilterEntry 7 }

tchRgFirewallMacFilterEnable OBJECT-TYPE
    SYNTAX      TruthValue
    MAX-ACCESS  read-write
    STATUS      current
    DESCRIPTION
        "True = Enable the Mac address filtering feature. False = disable.
        this Value is written to non-vol and set to false after a factory reset."
    DEFVAL { false }
    ::= { tchRgFirewallRules 4 }

tchRgFirewallMacFilterMode OBJECT-TYPE
    SYNTAX      INTEGER {
        block(0),
        permit(1)
        }
    MAX-ACCESS  read-write
    STATUS      current
    DESCRIPTION
        "block(0)- Macs listed in the tchRgFirewallMacFilterEntryTable will be blocked.
        permit(1)- Macs listed in the tchRgFirewallMacFilterEntryTable will be permitted.
        This value is written to non-vol and is set to block(0) after a factory reset."
    DEFVAL { 0 }
    ::= { tchRgFirewallRules 5 }

tchRgFirewallPortFilterEnable OBJECT-TYPE
    SYNTAX      TruthValue
    MAX-ACCESS  read-write
    STATUS      current
    DESCRIPTION
        "True = Enable the Port filtering feature. False = disable.
        this Value is written to non-vol and set to false after a factory reset."
    DEFVAL { false }
    ::= { tchRgFirewallRules 6 }

tchRgFirewallUrlKeywordFiltering   OBJECT IDENTIFIER ::=  { tchRgFirewallRules 7 }

tchRgFirewallUrlKeywordFilterEnable OBJECT-TYPE
    SYNTAX      TruthValue
    MAX-ACCESS  read-write
    STATUS      current
    DESCRIPTION
        "True = Enable the Url Keyword filtering feature. False = disable.
        this Value is written to non-vol and set to false after a factory reset."
    DEFVAL { false }
    ::= { tchRgFirewallUrlKeywordFiltering 1 }

tchRgFirewallUrlKeywordFilterTable  OBJECT-TYPE
    SYNTAX      SEQUENCE OF TchRgFirewallUrlKeywordFilterEntry
    MAX-ACCESS  not-accessible
    STATUS      current
    DESCRIPTION
        "A table of url and keyword rules that are denied from accessing Internet."
    ::= { tchRgFirewallUrlKeywordFiltering 2 }

tchRgFirewallUrlKeywordFilterEntry OBJECT-TYPE
    SYNTAX      TchRgFirewallUrlKeywordFilterEntry
    MAX-ACCESS  not-accessible
    STATUS      current
    DESCRIPTION
        "A row in the table that specifies a single station MAC address."
    INDEX   { tchRgFirewallUrlKeywordFilterIndex }
    ::= { tchRgFirewallUrlKeywordFilterTable 1 }

TchRgFirewallUrlKeywordFilterEntry ::=
    SEQUENCE    {
            tchRgFirewallUrlKeywordFilterIndex            INTEGER,
            tchRgFirewallUrlKeywordFilterRowStatus        RowStatus,
            tchRgFirewallUrlKeywordFilterMethod           INTEGER,
            tchRgFirewallUrlKeywordFilterMatch            OCTET STRING,
            tchRgFirewallUrlKeywordFilterAlwaysBlock      TruthValue,
            tchRgFirewallUrlKeywordFilterBlockStartTime   OCTET STRING,
            tchRgFirewallUrlKeywordFilterBlockEndTime     OCTET STRING,
            tchRgFirewallUrlKeywordFilterBlockDays        BITS
    }

tchRgFirewallUrlKeywordFilterIndex OBJECT-TYPE
    SYNTAX      INTEGER (1..20)
    MAX-ACCESS  not-accessible
    STATUS      current
    DESCRIPTION
            "The index"
    ::= { tchRgFirewallUrlKeywordFilterEntry 1 }

tchRgFirewallUrlKeywordFilterRowStatus OBJECT-TYPE
    SYNTAX      RowStatus
    MAX-ACCESS  read-create
    STATUS      current
    DESCRIPTION
            "The row status. A row can be destroyed.
             If the row is not used, set to notInService."
    ::= { tchRgFirewallUrlKeywordFilterEntry 2 }

tchRgFirewallUrlKeywordFilterMethod OBJECT-TYPE
    SYNTAX      INTEGER {
                url(1),
                keyword(2)
        }
    MAX-ACCESS  read-write
    STATUS      current
    DESCRIPTION
        "If url(1),deny access to specific websites (URLs)
        If keyword(2), deny access to websites containing specific words"
    ::= { tchRgFirewallUrlKeywordFilterEntry 3 }

tchRgFirewallUrlKeywordFilterMatch OBJECT-TYPE
    SYNTAX      OCTET STRING
    MAX-ACCESS  read-write
    STATUS      current
    DESCRIPTION
        "URLs or specific words according to Method set"
    ::= { tchRgFirewallUrlKeywordFilterEntry 4 }

tchRgFirewallUrlKeywordFilterAlwaysBlock OBJECT-TYPE
    SYNTAX      TruthValue
    MAX-ACCESS  read-write
    STATUS      current
    DESCRIPTION
        "If true(1), always be blocked, regardless of startTime, endTime and blockDays
        If false(2), blocked at time set in startTime, endTime and blockDays"
    DEFVAL { true }
    ::= { tchRgFirewallUrlKeywordFilterEntry 5 }

tchRgFirewallUrlKeywordFilterBlockStartTime OBJECT-TYPE
    SYNTAX      OCTET STRING (SIZE (5))
    MAX-ACCESS  read-write
    STATUS      current
    DESCRIPTION
        "24 Hour format HH:MM to set the start time to block"
    ::= { tchRgFirewallUrlKeywordFilterEntry 6 }

tchRgFirewallUrlKeywordFilterBlockEndTime OBJECT-TYPE
    SYNTAX      OCTET STRING (SIZE (5))
    MAX-ACCESS  read-write
    STATUS      current
    DESCRIPTION
        "24 Hour format HH:MM to set the end time to block"
    ::= { tchRgFirewallUrlKeywordFilterEntry 7 }

tchRgFirewallUrlKeywordFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block"
    ::= { tchRgFirewallUrlKeywordFilterEntry 8 }

-- Port forwarding

tchRgFirewallPortFwdTable OBJECT-TYPE
       SYNTAX      SEQUENCE OF TchRgFirewallPortFwdEntry
       MAX-ACCESS  not-accessible
       STATUS      current
       DESCRIPTION
               "This table is stored in non-vol and is empty
                after factory reset."
    ::= { tchRgFirewall 6 }

tchRgFirewallPortFwdEntry OBJECT-TYPE
    SYNTAX      TchRgFirewallPortFwdEntry
    MAX-ACCESS  not-accessible
    STATUS      current
    DESCRIPTION
            ""
    INDEX { tchRgFirewallPortFwdIndex }
    ::= { tchRgFirewallPortFwdTable 1 }

TchRgFirewallPortFwdEntry ::= SEQUENCE {
    tchRgFirewallPortFwdIndex              INTEGER,
    tchRgFirewallPortFwdRowStatus          RowStatus,
    tchRgFirewallPortFwdToAddress          IpAddress,
    tchRgFirewallPortFwdPortStart          InetPortNumber,
    tchRgFirewallPortFwdPortEnd            InetPortNumber,
    tchRgFirewallPortFwdProto              INTEGER,
    tchRgFirewallPortFwdSrvcName           SnmpAdminString,
    tchRgFirewallPortFwdExternalPortStart  InetPortNumber,
    tchRgFirewallPortFwdExternalPortEnd    InetPortNumber,
    tchRgFirewallPortFwdRemove             INTEGER,
    tchRgFirewallPortFwdAddressType        INTEGER
    }

tchRgFirewallPortFwdIndex OBJECT-TYPE
    SYNTAX      INTEGER (1..30)
    MAX-ACCESS  not-accessible
    STATUS      current
    DESCRIPTION
            "The index"
    ::= { tchRgFirewallPortFwdEntry 1 }

tchRgFirewallPortFwdRowStatus OBJECT-TYPE
    SYNTAX      RowStatus
    MAX-ACCESS  read-create
    STATUS      current
    DESCRIPTION
            "The row status. A row can be destroyed.
             If the row is not used, set to notInService."
    ::= { tchRgFirewallPortFwdEntry 2 }

tchRgFirewallPortFwdToAddress OBJECT-TYPE
    SYNTAX      IpAddress
    MAX-ACCESS  read-write
    STATUS      current
    DESCRIPTION
            "Valid address must be entered for a row to be created."
    ::= { tchRgFirewallPortFwdEntry 3 }

tchRgFirewallPortFwdPortStart OBJECT-TYPE
    SYNTAX      InetPortNumber
    MAX-ACCESS  read-write
    STATUS      current
    DESCRIPTION
            "Valid port must be entered for a row to be created."
    ::= { tchRgFirewallPortFwdEntry 4 }

tchRgFirewallPortFwdPortEnd OBJECT-TYPE
    SYNTAX      InetPortNumber
    MAX-ACCESS  read-write
    STATUS      current
    DESCRIPTION
            "Valid port must be entered for a row to be created."
    ::= { tchRgFirewallPortFwdEntry 5 }

tchRgFirewallPortFwdProto OBJECT-TYPE
    SYNTAX      INTEGER {
        udp(1),
        tcp(2),
        udpTcp(3)
        }
    MAX-ACCESS  read-write
    STATUS      current
    DESCRIPTION
            ""
    DEFVAL { 2 }
    ::= { tchRgFirewallPortFwdEntry 6 }

tchRgFirewallPortFwdSrvcName OBJECT-TYPE
    SYNTAX      SnmpAdminString
    MAX-ACCESS  read-write
    STATUS      current
    DESCRIPTION
            "Port forward service name for use with Puma-based products."
    ::= { tchRgFirewallPortFwdEntry 7 }

tchRgFirewallPortFwdExternalPortStart OBJECT-TYPE
    SYNTAX      InetPortNumber
    MAX-ACCESS  read-write
    STATUS      current
    DESCRIPTION
            "Valid port must be entered for a row to be created. This is the outside-facing start port for the portforward."
    ::= { tchRgFirewallPortFwdEntry 8 }

tchRgFirewallPortFwdExternalPortEnd OBJECT-TYPE
    SYNTAX      InetPortNumber
    MAX-ACCESS  read-write
    STATUS      current
    DESCRIPTION
            "Valid port must be entered for a row to be created. This is the outside-facing end port for the portforward."
    ::= { tchRgFirewallPortFwdEntry 9 }
	
tchRgFirewallPortFwdRemove OBJECT-TYPE
    SYNTAX      INTEGER {
                      false  (0),
                      true   (1),
                      all    (99)
                        }

      MAX-ACCESS    read-write
      STATUS        current
      DESCRIPTION
        "The default value is false(0).
         If set to true(1), then this port forwarding rule will be removed.
         If set to 99, then All port forwarding rules will be removed."
      ::= { tchRgFirewallPortFwdEntry 10 }
      
tchRgFirewallPortFwdAddressType OBJECT-TYPE
    SYNTAX      INTEGER {
                      Unknown  (0),
                      IPv4     (1),
                      IPv6     (2)
                        }

      MAX-ACCESS    read-write
      STATUS        current
      DESCRIPTION
        "The default value is Unknown(0).
         If set to 1, then tchRgFirewallPortFwdToAddress will be in IPv4.
         If set to 2, then tchRgFirewallPortFwdToAddress will be in IPv6"
      ::= { tchRgFirewallPortFwdEntry 11 }  

-- Port triggering

tchRgFirewallPortTrigTable OBJECT-TYPE
       SYNTAX      SEQUENCE OF TchRgFirewallPortTrigEntry
       MAX-ACCESS  not-accessible
       STATUS      current
       DESCRIPTION
               "This table is stored in non-vol and is empty
                after factory reset."
    ::= { tchRgFirewall 7 }

tchRgFirewallPortTrigEntry OBJECT-TYPE
    SYNTAX      TchRgFirewallPortTrigEntry
    MAX-ACCESS  not-accessible
    STATUS      current
    DESCRIPTION
            ""
    INDEX { tchRgFirewallPortTrigIndex }
    ::= { tchRgFirewallPortTrigTable 1 }

TchRgFirewallPortTrigEntry ::= SEQUENCE {
    tchRgFirewallPortTrigIndex              INTEGER,
    tchRgFirewallPortTrigRowStatus          RowStatus,
    tchRgFirewallPortTrigTriggerPortStart   InetPortNumber,
    tchRgFirewallPortTrigTriggerPortEnd     InetPortNumber,
    tchRgFirewallPortTrigTargetPortStart    InetPortNumber,
    tchRgFirewallPortTrigTargetPortEnd      InetPortNumber,
    tchRgFirewallPortTrigProto              INTEGER,
    tchRgFirewallPortTrigSrvcName           SnmpAdminString
    }

tchRgFirewallPortTrigIndex OBJECT-TYPE
    SYNTAX      INTEGER (1..10)
    MAX-ACCESS  not-accessible
    STATUS      current
    DESCRIPTION
            "The index"
    ::= { tchRgFirewallPortTrigEntry 1 }

tchRgFirewallPortTrigRowStatus OBJECT-TYPE
    SYNTAX      RowStatus
    MAX-ACCESS  read-create
    STATUS      current
    DESCRIPTION
            "The row status. A row can be destroyed.
             If the row is not used, set to notInService."
    ::= { tchRgFirewallPortTrigEntry 2 }


tchRgFirewallPortTrigTriggerPortStart OBJECT-TYPE
    SYNTAX      InetPortNumber
    MAX-ACCESS  read-write
    STATUS      current
    DESCRIPTION
            ""
    ::= { tchRgFirewallPortTrigEntry 3 }

tchRgFirewallPortTrigTriggerPortEnd OBJECT-TYPE
    SYNTAX      InetPortNumber
    MAX-ACCESS  read-write
    STATUS      current
    DESCRIPTION
            ""
    ::= { tchRgFirewallPortTrigEntry 4 }

tchRgFirewallPortTrigTargetPortStart OBJECT-TYPE
    SYNTAX      InetPortNumber
    MAX-ACCESS  read-write
    STATUS      current
    DESCRIPTION
            ""
    ::= { tchRgFirewallPortTrigEntry 5 }

tchRgFirewallPortTrigTargetPortEnd OBJECT-TYPE
    SYNTAX      InetPortNumber
    MAX-ACCESS  read-write
    STATUS      current
    DESCRIPTION
            ""
    ::= { tchRgFirewallPortTrigEntry 6 }

tchRgFirewallPortTrigProto OBJECT-TYPE
    SYNTAX      INTEGER {
        udp(1),
        tcp(2),
        udpTcp(3)
        }
    MAX-ACCESS  read-write
    STATUS      current
    DESCRIPTION
            ""
    DEFVAL { 2 }
    ::= { tchRgFirewallPortTrigEntry 7 }

tchRgFirewallPortTrigSrvcName OBJECT-TYPE
    SYNTAX      SnmpAdminString
    MAX-ACCESS  read-write
    STATUS      current
    DESCRIPTION
            "Port trigger service name for use with Puma-based products."
    ::= { tchRgFirewallPortTrigEntry 8 }

tchRgFirewallHttpBlockingEnable OBJECT-TYPE
    SYNTAX      TruthValue
    MAX-ACCESS  read-write
    STATUS      current
    DESCRIPTION
        "Enables or disables firewall HTTP blocking on the device."
    DEFVAL { false }
    ::= { tchRgFirewall 8 }

tchRgFirewallP2pBlockingEnable OBJECT-TYPE
    SYNTAX      TruthValue
    MAX-ACCESS  read-write
    STATUS      current
    DESCRIPTION
        "Enables or disables firewall P2P blocking on the device."
    DEFVAL { false }
    ::= { tchRgFirewall 9 }

tchRgFirewallIdentBlockingEnable OBJECT-TYPE
    SYNTAX      TruthValue
    MAX-ACCESS  read-write
    STATUS      current
    DESCRIPTION
        "Enables or disables firewall ident blocking on the device."
    DEFVAL { false }
    ::= { tchRgFirewall 10 }

tchRgFirewallIcmpBlockingEnable OBJECT-TYPE
    SYNTAX      TruthValue
    MAX-ACCESS  read-write
    STATUS      current
    DESCRIPTION
        "Enables or disables firewall ICMP blocking on the device."
    DEFVAL { false }
    ::= { tchRgFirewall 11 }

tchRgFirewallMulticastBlockingEnable OBJECT-TYPE
    SYNTAX      TruthValue
    MAX-ACCESS  read-write
    STATUS      current
    DESCRIPTION
        "Enables or disables firewall multicast blocking on the device."
    DEFVAL { false }
    ::= { tchRgFirewall 12 }
	
tchRgFirewallSecureDnsEnable OBJECT-TYPE
    SYNTAX      TruthValue
    MAX-ACCESS  read-write
    STATUS      current
	DESCRIPTION
	    "Enables/Disables the Secure DNS.
		If true(1), Secure DNS is Enabled.
		If false(2), Secure DNS is Disabled."
	DEFVAL { false }
    ::= { tchRgFirewall 13 }	
	
tchRgFirewallHttpsBlockingEnable OBJECT-TYPE
    SYNTAX      TruthValue
    MAX-ACCESS  read-write
    STATUS      current
    DESCRIPTION
        "Enables or disables firewall HTTPs blocking on the device."
    DEFVAL { false }
    ::= { tchRgFirewall 14 }

tchRgFirewallSecurityDoS OBJECT IDENTIFIER ::=  { tchRgFirewall 15 }

	   
tchRgFirewallDoSEnable OBJECT-TYPE
    SYNTAX      TruthValue
    MAX-ACCESS  read-write
    STATUS      current
    DESCRIPTION
        "True = Enable the DoS feature. False = disable.
        "
    
    ::= { tchRgFirewallSecurityDoS 1 }
	   
	   
tchRgFirewallDoS OBJECT-TYPE
    SYNTAX BITS {
        iCMPFlood(0),
		tCPSynFlood(1),
		uDPFlood(2),
		fINFlood(3),
		iPLand(4),
		iCMPSmurf(5),
		iPSpoof(6)
    }
    MAX-ACCESS    read-write
    STATUS        current
    DESCRIPTION
        "tchRgFirewallDoSEnable should be enabled for these to work.
		"
    ::= { tchRgFirewallSecurityDoS 2 }

tchRgFirewallIcmpFloodPackets OBJECT-TYPE
    SYNTAX      Unsigned32  (1..500)
    MAX-ACCESS read-write
    STATUS current
    DESCRIPTION
        "To set and get number of IP ICMP Flood packets per second"
    DEFVAL { 1 }
    ::= { tchRgFirewallSecurityDoS 3 }

tchRgFirewallTCPSynFloodPackets OBJECT-TYPE
    SYNTAX      Unsigned32  (1..500)
    MAX-ACCESS read-write
    STATUS current
    DESCRIPTION
        "To set and get number of IP TCP SYN packets per second"
    DEFVAL { 1 }
    ::= { tchRgFirewallSecurityDoS  4}

tchRgFirewallUdpFloodPackets OBJECT-TYPE
    SYNTAX      Unsigned32  (1..500)
    MAX-ACCESS read-write
    STATUS current
    DESCRIPTION
        "To set and get number of UDP packets per second"
    DEFVAL { 1 }
    ::= { tchRgFirewallSecurityDoS  5}

tchRgFirewallFinFloodPackets OBJECT-TYPE
    SYNTAX      Unsigned32  (1..500)
    MAX-ACCESS read-write
    STATUS current
    DESCRIPTION
        "To set and get number of Fin packets per second"
    DEFVAL { 1 }
    ::= { tchRgFirewallSecurityDoS  6}

tchRgFirewallApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until tchRgFirewallApplySettings is set to true or CM resets.
         Note: this applies only to the MIB objects that are stored
         in non-vol.
         Always returns false(2) when read."
    ::= { tchRgFirewall 1001 }

tchRgFirewallFactoryReset OBJECT-TYPE
    SYNTAX      TruthValue
    MAX-ACCESS  read-write
    STATUS      current
    DESCRIPTION
        "Set true(1) to restore default settings of firewall.
         Always returns false(2) when read."
    ::= { tchRgFirewall 1002 }

-- ===
-- RIP
-- ===

tchRgRip OBJECT IDENTIFIER ::=  { tchRg 5 }

tchRgRipBase OBJECT IDENTIFIER ::=  { tchRgRip 1 }

tchRgRipEnabled OBJECT-TYPE
    SYNTAX      TruthValue
    MAX-ACCESS  read-write
    STATUS      current
    DESCRIPTION
        "Enables or disables router information protocol support in the device."
    DEFVAL { false }
    ::= { tchRgRipBase 1 }

tchRgRipMd5AuthEnable    OBJECT-TYPE
    SYNTAX     TruthValue
    MAX-ACCESS read-write
    STATUS     current
    DESCRIPTION
        "Setting this object to true(1) causes the device to enable md5 auth"
    ::= { tchRgRipBase 2 }

tchRgRipMd5KeyId OBJECT-TYPE
    SYNTAX     INTEGER (0..255)
    MAX-ACCESS read-write
    STATUS     current
    DESCRIPTION
        "Key ID value for Md5 auth.
         This object return an empty string when read."
    ::= { tchRgRipBase 3 }

tchRgRipMd5KeyValue OBJECT-TYPE
    SYNTAX     OCTET STRING (SIZE(0..16))
    MAX-ACCESS read-write
    STATUS     current
    DESCRIPTION
        "MD5 Key Value"
    ::= { tchRgRipBase 4 }

tchRgRipInterval OBJECT-TYPE
    SYNTAX     INTEGER  (10..600)
    MAX-ACCESS read-write
    STATUS     current
    DESCRIPTION
        "Interval in Seconds for the Rip Reporting interval."
    ::= { tchRgRipBase 5 }

tchRgRipDestIpAddressType OBJECT-TYPE
    SYNTAX      InetAddressType
    MAX-ACCESS  read-write
    STATUS      current
    DESCRIPTION
        "The type of IP address assigned to the rgIpRipDestIpAddress."
    DEFVAL { ipv4 }
    ::= { tchRgRipBase 6 }

tchRgRipDestIpAddress OBJECT-TYPE
    SYNTAX      InetAddress
    MAX-ACCESS  read-write
    STATUS      current
    DESCRIPTION
        "Defines the RIP unicast destination IP Address for Rip Reports.
         If this value returns 0.0.0.0 then this is the default
         multicast IP address in the RFC (224.0.0.9)"
    ::= { tchRgRipBase 7 }

tchRgRipAuthType  OBJECT-TYPE
    SYNTAX      INTEGER {
        noAuth(1),
        simplePassword(2),
        md5(3)
        }
    MAX-ACCESS read-write
    STATUS     current
    DESCRIPTION
        "For use with puma-based products,
                NoAuth(1), no authentication,
                SimplePassword(2), simple plain password,
                MD5(3), md5 auth"
        DEFVAL { noAuth }
    ::= { tchRgRipBase 8 }

tchRgRipAuthSimplePassword OBJECT-TYPE
    SYNTAX     OCTET STRING
    MAX-ACCESS read-write
    STATUS     current
    DESCRIPTION
        "Simple password when auth type is 2"
    ::= { tchRgRipBase 9 }


-- ==========================
-- DMS specific configuration
-- ==========================

-- this tree exists only if DMS hardware is present

tchRgDmsSpecific OBJECT IDENTIFIER ::= { tchRg 6 }

tchRgDmsBase OBJECT IDENTIFIER ::= { tchRgDmsSpecific 1 }

tchRgDmsBaseSnmpPort OBJECT-TYPE
    SYNTAX      InetPortNumber
    MAX-ACCESS  read-write
    STATUS      current
    DESCRIPTION
            "Defines what port to use on the WAN IP address of the gateway
             to enable port forwarding for SNMP access to the DMS (on port
             161).
             Port 0 means port forwarding is disabled.
             Note: the entry for this does not appear in port forwarding
             table or on the web pages."
    DEFVAL { 0 }
    ::= { tchRgDmsBase 1 }

tchRgDmsBaseWebRedirect OBJECT-TYPE
    SYNTAX TruthValue
    MAX-ACCESS read-write
    STATUS current
    DESCRIPTION
         "This objects specifies if HTTP web page request should be
          redirected to DMS.
          The value of this object is stored in non-vol."
    DEFVAL { true }
    ::= { tchRgDmsBase 2 }

tchRgDmsProvisioning OBJECT IDENTIFIER ::= { tchRgDmsSpecific 2 }

tchRgDmsProvFilename OBJECT-TYPE
    SYNTAX SnmpAdminString
    MAX-ACCESS read-write
    STATUS current
    DESCRIPTION
        "Specifies the filename for DMS provisioning.
         The string is sent in DHCP OFFER and ACK as boot file to the DMS.
         If not set, boot file option is empty."
    DEFVAL { "" }
    ::= { tchRgDmsProvisioning 1 }

tchRgDmsProvServerType OBJECT-TYPE
    SYNTAX InetAddressType
    MAX-ACCESS read-write
    STATUS current
    DESCRIPTION
        "Specifies the type for IP address for DMS provisioning"
    DEFVAL { ipv4 }
    ::= { tchRgDmsProvisioning 2 }

tchRgDmsProvServer OBJECT-TYPE
    SYNTAX InetAddress
    MAX-ACCESS read-write
    STATUS current
    DESCRIPTION
        "Specifies the IP address for DMS provisioning.
         The address is sent in DHCP OFFER and ACK as next server to the DMS.
         If not set, the next server field is empty."
    DEFVAL  { '00000000'h }
    ::= { tchRgDmsProvisioning 3 }

tchRgDmsProvDhcpSecurity OBJECT-TYPE
    SYNTAX BITS {
        option-60(0),
        option-43-153(1)
        }
    MAX-ACCESS read-write
    STATUS current
    DESCRIPTION
        "Specifies what security features have to enabled for DMS
         to get the IP address from the gateway:
         0: SACMDMS must be present in DHCP DISCOVER option 60. If not set
            it is assumed there is no DMS. In this case the DMS will is
            treated as another CPE connected to LAN network.
         1: DHCP DISCOVER option 43.153 must be correct.
         This parameter is stored in non-vol and is 0x80 after factory
         reset."
    ::= { tchRgDmsProvisioning 4 }


tchRgDmsNameResolution OBJECT IDENTIFIER ::= { tchRgDmsSpecific 3 }

tchRgDmsNameResolutionName OBJECT-TYPE
    SYNTAX SnmpAdminString
    MAX-ACCESS read-write
    STATUS current
    DESCRIPTION
        "Specifies the DNS name for the DMS.
         Stored in non-vol and empty after factory reset."
    DEFVAL { "" }
    ::= { tchRgDmsNameResolution 1 }

tchRgDmsNameResolutionDeviceTarget OBJECT-TYPE
    SYNTAX INTEGER {
        disable(0),
        self(1),
        dms(2)
        }
    MAX-ACCESS read-write
    STATUS current
    DESCRIPTION
        "Specifies what IP address to resolve the name to.
         Stored in non-vol and set to disable(0) after factory reset."
    DEFVAL { 0 }
    ::= { tchRgDmsNameResolution 2 }


-- ===========================
-- MoCA specific configuration
-- ===========================

tchRgMocaExtSpecific OBJECT IDENTIFIER ::= { tchRg 7 }

tchRgMocaExtBase OBJECT IDENTIFIER ::= { tchRgMocaExtSpecific 1 }

tchRgMocaExtProvisioning OBJECT IDENTIFIER ::= { tchRgMocaExtSpecific 2 }

tchRgMocaExtProvFilename OBJECT-TYPE
    SYNTAX SnmpAdminString
    MAX-ACCESS read-write
    STATUS current
    DESCRIPTION
        "Specifies the filename for extender provisioning.
         The string is sent in DHCP OFFER and ACK as boot file to the extender.
         If not set, boot file option is empty."
    DEFVAL { "" }
    ::= { tchRgMocaExtProvisioning 1 }

tchRgMocaExtProvServerType OBJECT-TYPE
    SYNTAX InetAddressType
    MAX-ACCESS read-write
    STATUS current
    DESCRIPTION
        "Specifies the type for IP address for extender provisioning"
    DEFVAL { ipv4 }
    ::= { tchRgMocaExtProvisioning 2 }

tchRgMocaExtProvServer OBJECT-TYPE
    SYNTAX InetAddress
    MAX-ACCESS read-write
    STATUS current
    DESCRIPTION
        "Specifies the IP address for extender provisioning.
         The address is sent in DHCP OFFER and ACK as next server to the extender.
         If not set, the next server field is empty."
    DEFVAL  { '00000000'h } -- 0.0.0.0
    ::= { tchRgMocaExtProvisioning 3 }



-- ===========
-- QoS related
-- ===========


TchRgQosTosToPriority ::= TEXTUAL-CONVENTION
    STATUS       current
    DESCRIPTION
         "Specifies mapping for each ToS value to 2-bit (4 value) priority.
          -h is the high significant bit, -l is the low significant bit."
    SYNTAX BITS {
        tos-fc-h(0),
        tos-fc-l(1),
        tos-f8-h(2),
        tos-f8-l(3),
        tos-f4-h(4),
        tos-f4-l(5),
        tos-f0-h(6),
        tos-f0-l(7),
        tos-ec-h(8),
        tos-ec-l(9),
        tos-e8-h(10),
        tos-e8-l(11),
        tos-e4-h(12),
        tos-e4-l(13),
        tos-e0-h(14),
        tos-e0-l(15),
        tos-dc-h(16),
        tos-dc-l(17),
        tos-d8-h(18),
        tos-d8-l(19),
        tos-d4-h(20),
        tos-d4-l(21),
        tos-d0-h(22),
        tos-d0-l(23),
        tos-cc-h(24),
        tos-cc-l(25),
        tos-c8-h(26),
        tos-c8-l(27),
        tos-c4-h(28),
        tos-c4-l(29),
        tos-c0-h(30),
        tos-c0-l(31),
        tos-bc-h(32),
        tos-bc-l(33),
        tos-b8-h(34),
        tos-b8-l(35),
        tos-b4-h(36),
        tos-b4-l(37),
        tos-b0-h(38),
        tos-b0-l(39),
        tos-ac-h(40),
        tos-ac-l(41),
        tos-a8-h(42),
        tos-a8-l(43),
        tos-a4-h(44),
        tos-a4-l(45),
        tos-a0-h(46),
        tos-a0-l(47),
        tos-9c-h(48),
        tos-9c-l(49),
        tos-98-h(50),
        tos-98-l(51),
        tos-94-h(52),
        tos-94-l(53),
        tos-90-h(54),
        tos-90-l(55),
        tos-8c-h(56),
        tos-8c-l(57),
        tos-88-h(58),
        tos-88-l(59),
        tos-84-h(60),
        tos-84-l(61),
        tos-80-h(62),
        tos-80-l(63),
        tos-7c-h(64),
        tos-7c-l(65),
        tos-78-h(66),
        tos-78-l(67),
        tos-74-h(68),
        tos-74-l(69),
        tos-70-h(70),
        tos-70-l(71),
        tos-6c-h(72),
        tos-6c-l(73),
        tos-68-h(74),
        tos-68-l(75),
        tos-64-h(76),
        tos-64-l(77),
        tos-60-h(78),
        tos-60-l(79),
        tos-5c-h(80),
        tos-5c-l(81),
        tos-58-h(82),
        tos-58-l(83),
        tos-54-h(84),
        tos-54-l(85),
        tos-50-h(86),
        tos-50-l(87),
        tos-4c-h(88),
        tos-4c-l(89),
        tos-48-h(90),
        tos-48-l(91),
        tos-44-h(92),
        tos-44-l(93),
        tos-40-h(94),
        tos-40-l(95),
        tos-3c-h(96),
        tos-3c-l(97),
        tos-38-h(98),
        tos-38-l(99),
        tos-34-h(100),
        tos-34-l(101),
        tos-30-h(102),
        tos-30-l(103),
        tos-2c-h(104),
        tos-2c-l(105),
        tos-28-h(106),
        tos-28-l(107),
        tos-24-h(108),
        tos-24-l(109),
        tos-20-h(110),
        tos-20-l(111),
        tos-1c-h(112),
        tos-1c-l(113),
        tos-18-h(114),
        tos-18-l(115),
        tos-14-h(116),
        tos-14-l(117),
        tos-10-h(118),
        tos-10-l(119),
        tos-0c-h(120),
        tos-0c-l(121),
        tos-08-h(122),
        tos-08-l(123),
        tos-04-h(124),
        tos-04-l(125),
        tos-00-h(126),
        tos-00-l(127)
        }

TchRgQosVlanToPriority ::= TEXTUAL-CONVENTION
    STATUS       current
    DESCRIPTION
         "Specifies mapping for each VLAN value to 2-bit (4 value) priorty.
          -h is the high significant bit, -l is the low significant bit."
    SYNTAX BITS {
        vlan-7-h(0),
        vlan-7-l(1),
        vlan-6-h(2),
        vlan-6-l(3),
        vlan-5-h(4),
        vlan-5-l(5),
        vlan-4-h(6),
        vlan-4-l(7),
        vlan-3-h(8),
        vlan-3-l(9),
        vlan-2-h(10),
        vlan-2-l(11),
        vlan-1-h(12),
        vlan-1-l(13),
        vlan-0-h(14),
        vlan-0-l(15)
    }

tchRgQos OBJECT IDENTIFIER ::=  { tchRg 8 }

tchRgQosLan OBJECT IDENTIFIER ::=  { tchRgQos 1 }

tchRgQosLanBase OBJECT IDENTIFIER ::=  { tchRgQosLan 1 }

tchRgQosLanIgmpSnooping OBJECT-TYPE
    SYNTAX INTEGER {
        disable(0),
        enable(1)
        }
    MAX-ACCESS read-write
    STATUS current
    DESCRIPTION
        "Controls IGMP snooping feature on the LAN side."
    DEFVAL { 1 }
    ::= { tchRgQosLanBase 1 }


tchRgQosLanSwitch OBJECT IDENTIFIER ::=  { tchRgQosLan 2 }

tchRgQosLanSwitchPortIndex OBJECT-TYPE
    SYNTAX INTEGER (0..4)
    MAX-ACCESS not-accessible
    STATUS current
    DESCRIPTION
        "Port index in the switch. Index 0 is the connection to the router chip."
    ::= { tchRgQosLanSwitch 1 }


tchRgQosLanSwitchEgressScheduler OBJECT-TYPE
    SYNTAX INTEGER {
        sp(0),
        wrr(1),
        sp-wrr(2)
        }
    MAX-ACCESS read-write
    STATUS current
    DESCRIPTION
        "Sets the scheduling algorithm for egress queues on the switch.
         sp(0): use strict priority
         wrr(1): use weighted round robin, the weigths are 8, 4, 2, 1.
         sp-wrr(2): use SP for highest priority queue and WRR with weights
                    4, 2, 1 for lower priority queues."
    DEFVAL { 0 }
    ::= { tchRgQosLanSwitch 2 }


tchRgQosSwitchClassPriorityTable OBJECT-TYPE
       SYNTAX      SEQUENCE OF TchRgQosSwitchClassPriorityEntry
       MAX-ACCESS  not-accessible
       STATUS      current
       DESCRIPTION
               "This table determines which classifiers are used for frame
                priority determination in the switch."
    ::= { tchRgQosLanSwitch 3 }

tchRgQosSwitchClassPriorityEntry OBJECT-TYPE
    SYNTAX      TchRgQosSwitchClassPriorityEntry
    MAX-ACCESS  not-accessible
    STATUS      current
    DESCRIPTION
            ""
    INDEX { tchRgQosLanSwitchPortIndex }
    ::= { tchRgQosSwitchClassPriorityTable 1 }

TchRgQosSwitchClassPriorityEntry ::= SEQUENCE {
    tchRgQosSwitchClassPriorityEnable  BITS,
    tchRgQosSwitchClassPriorityPort    INTEGER,
    tchRgQosSwitchClassPriorityDa      INTEGER,
    tchRgQosSwitchClassPriorityVlan    INTEGER,
    tchRgQosSwitchClassPriorityTos     INTEGER,
    tchRgQosSwitchClassPrioritySetPort BITS,
    tchRgQosSwitchClassPrioritySetDa   INTEGER,
    tchRgQosSwitchClassPrioritySetVlan BITS,
    tchRgQosSwitchClassPrioritySetTos  BITS
    }

tchRgQosSwitchClassPriorityEnable OBJECT-TYPE
    SYNTAX BITS {
        port(0),
        dst-mac(1),
        vlan(2),
        tos(3)
    }
    MAX-ACCESS  not-accessible
    STATUS      current
    DESCRIPTION
            "Defines which classifiers to use for determinig egress frame priority.
             If more than one is selected, the order for classification is determined
             by the other MIB objects.
             port(0): priority is determined by the ingress port
             dst-mac(1): priority is determined by destination MAC address - not implemented
             vlan(2): priority is determined by IEEE 802.1p
             tos(3): priorty is determined by IP ToS (IPv4) or IP TC (IPv6)"
    -- DEFVAL { '20'h }
    DEFVAL { { vlan } }
    ::= { tchRgQosSwitchClassPriorityEntry 1 }

tchRgQosSwitchClassPriorityPort OBJECT-TYPE
    SYNTAX      INTEGER (0..3)
    MAX-ACCESS  read-write
    STATUS      current
    DESCRIPTION
            "Defines priority of port classifier lookup.
             Priority 0 is the highest."
    DEFVAL { 2 }
    ::= { tchRgQosSwitchClassPriorityEntry 2 }

tchRgQosSwitchClassPriorityDa OBJECT-TYPE
    SYNTAX      INTEGER (0..3)
    MAX-ACCESS  not-accessible
    STATUS      current
    DESCRIPTION
            "Defines priority of DST MAC classifier lookup.
             Priority 0 is the highest.
             This is not implemented."
    DEFVAL { 3 }
    ::= { tchRgQosSwitchClassPriorityEntry 3 }

tchRgQosSwitchClassPriorityVlan OBJECT-TYPE
    SYNTAX      INTEGER (0..3)
    MAX-ACCESS  read-write
    STATUS      current
    DESCRIPTION
            "Defines priority of 802.1p classifier lookup.
             Priority 0 is the highest."
    DEFVAL { 0 }
    ::= { tchRgQosSwitchClassPriorityEntry 4 }

tchRgQosSwitchClassPriorityTos OBJECT-TYPE
    SYNTAX      INTEGER (0..3)
    MAX-ACCESS  read-write
    STATUS      current
    DESCRIPTION
            "Defines priority of ToS/TC classifier lookup.
             Priority 0 is the highest."
    DEFVAL { 1 }
    ::= { tchRgQosSwitchClassPriorityEntry 5 }

tchRgQosSwitchClassPrioritySetPort OBJECT-TYPE
    SYNTAX BITS {
        port-0-h(0),
        port-0-l(1),
        port-1-h(2),
        port-1-l(3),
        port-2-h(4),
        port-2-l(5),
        port-3-h(6),
        port-3-l(7),
        port-4-h(8),
        port-4-l(9)
        }
    MAX-ACCESS  read-write
    STATUS      current
    DESCRIPTION
            "This classifier sets the frame priority for defined ingress port.
             -h is the high significant bit, -l is the low significant bit."
    DEFVAL { { } }
    ::= { tchRgQosSwitchClassPriorityEntry 6 }

tchRgQosSwitchClassPrioritySetDa OBJECT-TYPE
    SYNTAX      INTEGER
    MAX-ACCESS  not-accessible
    STATUS      current
    DESCRIPTION
            "This is not implemented."
    DEFVAL { 0 }
    ::= { tchRgQosSwitchClassPriorityEntry 7 }

tchRgQosSwitchClassPrioritySetVlan OBJECT-TYPE
    SYNTAX      TchRgQosVlanToPriority
    MAX-ACCESS  read-write
    STATUS      current
    DESCRIPTION
            "This classifier sets the frame priority for each 802.1p priority."
    -- DEFVAL { 'fa50'h }
    DEFVAL { { vlan-7-h, vlan-7-l, vlan-6-h, vlan-6-l, vlan-5-h, vlan-4-h, vlan-3-l, vlan-2-l } }
    ::= { tchRgQosSwitchClassPriorityEntry 8 }

tchRgQosSwitchClassPrioritySetTos OBJECT-TYPE
    SYNTAX      TchRgQosTosToPriority
    MAX-ACCESS  read-write
    STATUS      current
    DESCRIPTION
            "This classifier sets the frame priority for each ToS or TC.
            The default value is 0xffffffffaaaaaaaa5555555500000000."
    -- DEFVAL { 'ffffffffaaaaaaaa5555555500000000'h }
    ::= { tchRgQosSwitchClassPriorityEntry 9 }

tchRgQosEnable OBJECT-TYPE
    SYNTAX INTEGER {
        disable(0),
        enable(1)
        }
    MAX-ACCESS  read-write
    STATUS      current
    DESCRIPTION
            "This will enable QoS classification for use with tchRgQosDestIp."
    DEFVAL { 0 }
    ::= { tchRgQosLan 3 }

tchRgQosDestIp OBJECT-TYPE
    SYNTAX      IpAddress
    MAX-ACCESS  read-write
    STATUS      current
    DESCRIPTION
            "This will set the IP address that has higher QoS priority."
    ::= { tchRgQosLan 4 }

-- ================================
-- HomePlug AV specific information
-- ================================

tchRgHomePlugAV OBJECT IDENTIFIER ::=  { tchRg 9 }

tchRgHomePlugAVBasicInfoTable OBJECT-TYPE
    SYNTAX SEQUENCE OF TchRgHomePlugAVBasicInfoEntry
    MAX-ACCESS      not-accessible
    STATUS          current
    DESCRIPTION
            "HomePlugAV basic information"
    ::= { tchRgHomePlugAV 1 }

tchRgHomePlugAVBasicInfoEntry OBJECT-TYPE
    SYNTAX          TchRgHomePlugAVBasicInfoEntry
    MAX-ACCESS      not-accessible
    STATUS          current
    DESCRIPTION
            "HomePlugAV basic information list"
    INDEX { tchRgHPAVBasicInfoIndex }
    ::= { tchRgHomePlugAVBasicInfoTable 1 }

 TchRgHomePlugAVBasicInfoEntry ::= SEQUENCE {
    tchRgHPAVBasicInfoIndex        INTEGER,
    tchRgHPAVBasicInfoNetworkID    OCTET STRING,
    tchRgHPAVBasicInfoCCo          MacAddress
    }

tchRgHPAVBasicInfoIndex OBJECT-TYPE
    SYNTAX          INTEGER (0..20)
    MAX-ACCESS      read-only
    STATUS          current
    DESCRIPTION
        "The index of HomePlugAV basic information"
    ::= { tchRgHomePlugAVBasicInfoEntry 1 }

tchRgHPAVBasicInfoNetworkID OBJECT-TYPE
    SYNTAX          OCTET STRING (SIZE(0..32))
    MAX-ACCESS      read-only
    STATUS          current
    DESCRIPTION
        "The information of network ID"
    ::= { tchRgHomePlugAVBasicInfoEntry 2 }

tchRgHPAVBasicInfoCCo OBJECT-TYPE
    SYNTAX          MacAddress
    MAX-ACCESS      read-only
    STATUS          current
    DESCRIPTION
        "The information of central coordinator"
    ::= { tchRgHomePlugAVBasicInfoEntry 3 }

tchRgHomePlugAVDeviceTable OBJECT-TYPE
    SYNTAX SEQUENCE OF TchRgHomePlugAVDeviceEntry
    MAX-ACCESS      not-accessible
    STATUS          current
    DESCRIPTION
            "HomePlugAV on the device side"
    ::= { tchRgHomePlugAV 2 }

tchRgHomePlugAVDeviceEntry OBJECT-TYPE
    SYNTAX          TchRgHomePlugAVDeviceEntry
    MAX-ACCESS      not-accessible
    STATUS          current
    DESCRIPTION
            "HomePlugAV list on the device side."
    INDEX { tchRgHPAVBasicInfoIndex, tchRgHPAVDeviceIndex }
    ::= { tchRgHomePlugAVDeviceTable 1 }

TchRgHomePlugAVDeviceEntry ::= SEQUENCE {
    tchRgHPAVDeviceIndex        INTEGER,
--    tchRgHPAVDeviceNetworkID    OCTET STRING,
--    tchRgHPAVDeviceCCo          MacAddress,
    tchRgHPAVDeviceStatus       INTEGER,
    tchRgHPAVDeviceMACAddr      MacAddress,
    tchRgHPAVDeviceAdaptor      OCTET STRING,
    tchRgHPAVDeviceVendor       OCTET STRING,
    tchRgHPAVDeviceFirmware     OCTET STRING,
    tchRgHPAVDeviceChipset      OCTET STRING,
    tchRgHPAVDeviceTx           INTEGER,
    tchRgHPAVDeviceRx           INTEGER,
    tchRgHPAVDeviceTime         Integer32
    }

tchRgHPAVDeviceIndex OBJECT-TYPE
    SYNTAX          INTEGER (0..32)
    MAX-ACCESS      read-only
    STATUS          current
    DESCRIPTION
        "The index of the HomPlugAV on the device side"
    ::= { tchRgHomePlugAVDeviceEntry 1 }

tchRgHPAVDeviceStatus OBJECT-TYPE
    SYNTAX          INTEGER {
                        success(0),
                        failure(1)
                    }
    MAX-ACCESS      read-only
    STATUS          current
    DESCRIPTION
        "The status of HomPlugAV that indication if adaptor was discovered during last scan"
    ::= { tchRgHomePlugAVDeviceEntry 2 }

tchRgHPAVDeviceMACAddr OBJECT-TYPE
    SYNTAX          MacAddress
    MAX-ACCESS      read-only
    STATUS          current
    DESCRIPTION
        "MAC address assigned to dectected HP adaptor"
    ::= { tchRgHomePlugAVDeviceEntry 3 }

tchRgHPAVDeviceAdaptor OBJECT-TYPE
    SYNTAX          OCTET STRING (SIZE(0..6))
    MAX-ACCESS      read-only
    STATUS          current
    DESCRIPTION
        "Indication if the listed device is ether a local or remote HP adaptor"
    ::= { tchRgHomePlugAVDeviceEntry 4 }

tchRgHPAVDeviceVendor OBJECT-TYPE
    SYNTAX          OCTET STRING (SIZE(0..32))
    MAX-ACCESS      read-only
    STATUS          current
    DESCRIPTION
        "Textual representation of the manufacturer"
    ::= { tchRgHomePlugAVDeviceEntry 5 }

tchRgHPAVDeviceFirmware OBJECT-TYPE
    SYNTAX          OCTET STRING (SIZE(0..64))
    MAX-ACCESS      read-only
    STATUS          current
    DESCRIPTION
        "Textual representation of the firmware version of the HP adaptor"
    ::= { tchRgHomePlugAVDeviceEntry 6 }

tchRgHPAVDeviceChipset OBJECT-TYPE
    SYNTAX          OCTET STRING (SIZE(0..32))
    MAX-ACCESS      read-only
    STATUS          current
    DESCRIPTION
        "Textual representation of the chipset of HP adaptor"
    ::= { tchRgHomePlugAVDeviceEntry 7 }

tchRgHPAVDeviceTx OBJECT-TYPE
    SYNTAX          INTEGER
    MAX-ACCESS      read-only
    STATUS          current
    DESCRIPTION
        "Tx PHY rate as reported by the HP adaptor during the last scan [Mbps]"
    ::= { tchRgHomePlugAVDeviceEntry 8 }

tchRgHPAVDeviceRx OBJECT-TYPE
    SYNTAX          INTEGER
    MAX-ACCESS      read-only
    STATUS          current
    DESCRIPTION
        "Rx PHY rate as reported by the HP adaptor during the last scan [Mbps]"
    ::= { tchRgHomePlugAVDeviceEntry 9 }

tchRgHPAVDeviceTime OBJECT-TYPE
    SYNTAX          Integer32
    MAX-ACCESS      read-only
    STATUS          current
    DESCRIPTION
        "SysUpTime of the HGW when the table was last updated for this adaptor"
    ::= { tchRgHomePlugAVDeviceEntry 10 }

tchRgHomePlugAVHostTable OBJECT-TYPE
    SYNTAX SEQUENCE OF TchRgHomePlugAVHostEntry
    MAX-ACCESS      not-accessible
    STATUS          current
    DESCRIPTION
            "HomePlugAV on the host side"
    ::= { tchRgHomePlugAV 3 }

tchRgHomePlugAVHostEntry OBJECT-TYPE
    SYNTAX          TchRgHomePlugAVHostEntry
    MAX-ACCESS      not-accessible
    STATUS          current
    DESCRIPTION
            "HomePlugAV list on the host side."
    INDEX { tchRgHPAVDHostIndex }
    ::= { tchRgHomePlugAVHostTable 1 }

TchRgHomePlugAVHostEntry ::= SEQUENCE {
    tchRgHPAVDHostIndex        INTEGER,
    tchRgHPAVHostBridgedMAC    MacAddress
    }

tchRgHPAVDHostIndex OBJECT-TYPE
    SYNTAX          INTEGER (0..32)
    MAX-ACCESS      read-only
    STATUS          current
    DESCRIPTION
        "The index of the HomPlugAV on the device side"
    ::= { tchRgHomePlugAVHostEntry 1 }

tchRgHPAVHostBridgedMAC OBJECT-TYPE
    SYNTAX          MacAddress
    MAX-ACCESS      read-only
    STATUS          current
    DESCRIPTION
        "MAC address of the device behind the HP Apdator"
    ::= { tchRgHomePlugAVHostEntry 2 }

tchRgHomePlugAVPollRate OBJECT-TYPE
    SYNTAX          INTEGER
    MAX-ACCESS      read-write
    STATUS          current
    DESCRIPTION
            "Time between the different network scans"
    DEFVAL {0}
    ::=  { tchRgHomePlugAV 4 }

tchRgHomePlugAVClearTable OBJECT-TYPE
    SYNTAX          INTEGER {
                        disable (0),
                        enable (1)
                    }
    MAX-ACCESS      read-write
    STATUS          current
    DESCRIPTION
            "Clean content of the table and restart scan and scan schedule"
    DEFVAL {0}
    ::=  { tchRgHomePlugAV 5 }

tchRgHomePlugAVRefreshTable OBJECT-TYPE
    SYNTAX          INTEGER {
                        disable (0),
                        enable (1)
                    }
    MAX-ACCESS      read-write
    STATUS          current
    DESCRIPTION
            "Perform an additional scan without interfering with the scan schedule"
    DEFVAL {0}
    ::=  { tchRgHomePlugAV 6 }

-- ================================
-- L2TP specific information
-- ================================

tchRgL2TP OBJECT IDENTIFIER ::=  { tchRg 10 }

tchRgL2TPOperMode OBJECT-TYPE
    SYNTAX      INTEGER {
                l2TPDisable(0),
                l2TPv2client(1),
                l2TPv2server(2),
                l2TPv3client(3)
    }
    MAX-ACCESS  read-write
    STATUS      current
    DESCRIPTION
        "L2TPDisable(0) - Disables l2tp client or server Functionality
         L2TPv2client(1) - Enables l2tpv2 client Functionality
         L2TPv2server(2) - Enables l2tpv2 server Functionality
         L2TPv3client(3) - Enables l2tpv3 client Functionality"
     ::= { tchRgL2TP 1 }

-- L2TPv2 Client Mode START

tchRgL2TPv2Client OBJECT IDENTIFIER ::=  { tchRgL2TP 2 }

tchRgL2TPv2PPPServerAddressType OBJECT-TYPE
    SYNTAX      InetAddressType{
        unknown(0),
        ipv4(1),
        ipv6(2)
    }
    MAX-ACCESS  read-write
    STATUS      current
    DESCRIPTION
            "This MIB defines the type of internet address to be used for the L2TP Server.
            0:  An unknown address type.  This value MUST
                be used if the value of the corresponding
                InetAddress object is a zero-length string.
                It may also be used to indicate an IP address
                that is not in one of the formats defined
                below.
            1 : IPv4 L2TP Server Address
            2 : IPv6 L2TP Server Address (reserved for future support)
            NOTE: The default value of 1 indicates support for IPv4 IP address."
    DEFVAL { ipv4 }
    ::= { tchRgL2TPv2Client 1 }

tchRgL2TPv2PPPServerAddress OBJECT-TYPE
    SYNTAX      InetAddress
    MAX-ACCESS  read-write
    STATUS      current
    DESCRIPTION
            "IP address of the remote endpoint L2TP server."
    ::= { tchRgL2TPv2Client 2 }


tchRgL2TPv2PPPUsername OBJECT-TYPE
    SYNTAX      OCTET STRING (SIZE(0..32))
    MAX-ACCESS  read-write
    STATUS      current
    DESCRIPTION
            "PPPUsername as in the PPP Server user list"
    ::= { tchRgL2TPv2Client 3 }


tchRgL2TPv2PPPPassword OBJECT-TYPE
    SYNTAX      OCTET STRING (SIZE(0..32))
    MAX-ACCESS  read-write
    STATUS      current
    DESCRIPTION
            "PPPPassword set for the user on the PPP Server it is trying to connect"
    ::= { tchRgL2TPv2Client 4 }

-- L2TPv2 Client Mode END

-- L2TPv2 Server Mode START

tchRgL2TPv2Server OBJECT IDENTIFIER ::=  { tchRgL2TP 3 }

tchRgL2TPv2ClientTable OBJECT-TYPE
    SYNTAX SEQUENCE OF TchRgDeviceL2TPv2ClientEntry
    MAX-ACCESS not-accessible
    STATUS current
    DESCRIPTION
            "L2TP client table when tchRgL2TPOperMode set to operate in l2tpv2 server mode "
    ::= { tchRgL2TPv2Server 1 }

tchRgL2TPv2ClientEntry OBJECT-TYPE
    SYNTAX      TchRgDeviceL2TPv2ClientEntry
    MAX-ACCESS  not-accessible
    STATUS     current
    DESCRIPTION
            ""
    INDEX { IMPLIED tchRgL2TPv2ClientIndex }
    ::= { tchRgL2TPv2ClientTable 1 }

TchRgDeviceL2TPv2ClientEntry ::= SEQUENCE {
    tchRgL2TPv2ClientIndex       INTEGER,
    tchRgL2TPv2ClientPppUsername OCTET STRING,
    tchRgL2TPv2ClientPppPassword OCTET STRING
    }

tchRgL2TPv2ClientIndex OBJECT-TYPE
    SYNTAX      INTEGER  (1..10)
    MAX-ACCESS  not-accessible
    STATUS      current
    DESCRIPTION
        "The unique index value of a row in this table."
    ::= { tchRgL2TPv2ClientEntry 1 }


tchRgL2TPv2ClientPppUsername OBJECT-TYPE
    SYNTAX      OCTET STRING (SIZE(0..32))
    MAX-ACCESS  read-write
    STATUS      current
    DESCRIPTION
            "Add the PPP username here. Remote client trying to connect should be present on this list"
    ::= { tchRgL2TPv2ClientEntry 2 }

tchRgL2TPv2ClientPppPassword OBJECT-TYPE
    SYNTAX      OCTET STRING (SIZE(0..32))
    MAX-ACCESS  read-write
    STATUS      current
    DESCRIPTION
            "Set the PPP user's password. Remote client trying to connect will be checked if it is a valid user"
    ::= { tchRgL2TPv2ClientEntry 3 }

tchRgL2TPv2ServerPreSharedPhrase OBJECT-TYPE
    SYNTAX      OCTET STRING (SIZE(0..32))
    MAX-ACCESS  read-write
    STATUS      current
    DESCRIPTION
            "Preshared Phrase needs to match between the server and the client in order for a tunnel to setup successfully"
    ::= { tchRgL2TPv2Server 2 }

-- L2TPv2 Server Mode END


-- L2TPv3 Client Mode START

tchRgL2TPv3Client OBJECT IDENTIFIER ::=  { tchRgL2TP 4 }

tchRgL2TPv3TunnelInterface OBJECT-TYPE
    SYNTAX    INTEGER {
                allEthernet(0),
                ethernet-1(1),
                ethernet-2(2),
                ethernet-3(3),
                ethernet-4(4),
                uSB(5),
                primarySSID(6),
                guestSSID-1(7),
                guestSSID-2(8),
                guestSSID-3(9),
                guestSSID-4(10),
                guestSSID-5(11),
                guestSSID-6(12),
                guestSSID-7(13)
    }
    MAX-ACCESS  read-write
    STATUS      current
    DESCRIPTION
            "allEthernet(0) represents the entire ethernet switch.
            ethernet-1 through ethernet-4 represent each individual ethernet switchport
            Sets the appropriate Tunnel endpoint interface.
            Note: USB(1) is for future support and must not be set"
    ::= { tchRgL2TPv3Client 1 }

tchRgL2TPv3Authentication OBJECT-TYPE
    SYNTAX  INTEGER {
            disable(0),
            enable(1)
        }
    MAX-ACCESS  read-write
    STATUS      current
    DESCRIPTION
            "Enable/ Disable Authentication used while setting up the tunnel"
    ::= { tchRgL2TPv3Client 2 }

tchRgL2TPv3DigestValue OBJECT-TYPE
    SYNTAX INTEGER {
                md5(0),
                sha-1(1)
    }
    MAX-ACCESS  read-write
    STATUS      current
    DESCRIPTION
            "Sets the appropriate Digest Value 0-MD5 or 1-SHA-1"
    ::= { tchRgL2TPv3Client 3 }

tchRgL2TPv3SharedSecret OBJECT-TYPE
    SYNTAX OCTET STRING (SIZE(0..32))
    MAX-ACCESS  read-write
    STATUS      current
    DESCRIPTION
            "Sets the Shared Secret to be used between server and client"
    ::= { tchRgL2TPv3Client 4 }

tchRgL2TPv3EndpointAddressType OBJECT-TYPE
    SYNTAX  InetAddressType{
        unknown(0),
        ipv4(1),
        ipv6(2)
    }
    MAX-ACCESS  read-write
    STATUS      current
    DESCRIPTION
            "This MIB defines the type of internet address to be used for the L2TP Server.
            0:  An unknown address type.  This value MUST
                be used if the value of the corresponding
                InetAddress object is a zero-length string.
                It may also be used to indicate an IP address
                that is not in one of the formats defined
                below.
            1 : IPv4 L2TP Server Address
            2 : IPv6 L2TP Server Address (reserved for future support)
            NOTE: The default value of 1 indicates support for IPv4 IP address."
    DEFVAL { ipv4 }
    ::= { tchRgL2TPv3Client 5 }

tchRgL2TPv3EndpointAddress OBJECT-TYPE
    SYNTAX InetAddress
    MAX-ACCESS  read-write
    STATUS      current
    DESCRIPTION
            "Set the Router's WAN MAN IP Address"
    ::= { tchRgL2TPv3Client 6 }

tchRgL2TPv3VirtualCircuitId OBJECT-TYPE
    SYNTAX   Integer32
    MAX-ACCESS  read-write
    STATUS      current
    DESCRIPTION
            "Sets the 32-bit Virtual Circuit Id(VC ID). for ex: 123"
    ::= { tchRgL2TPv3Client 7 }

tchRgL2TPv3CookieSize OBJECT-TYPE
    SYNTAX INTEGER {
                noCookie(0),
                size4(1),
                size8(2)
    }
    MAX-ACCESS  read-write
    STATUS      current
    DESCRIPTION
            "Sets the Cookie Size. for ex: 0 - No Cookie"
    ::= { tchRgL2TPv3Client 8 }

tchRgL2TPApplySettings OBJECT-TYPE
    SYNTAX      TruthValue
    MAX-ACCESS  read-write
    STATUS      current
    DESCRIPTION
        "If set to true(1), then RG will reboot and apply new L2TP settings.
         Before setting the value to true, MIBs modified in the MIB
         tree are stored in non-vol and will not modify RG operation
         until tchRgL2TPApplySettings is set to true or CM resets.
         Note: this applies only to the MIB objects that are stored
         in non-vol.
         Always returns false(2) when read."
   ::= { tchRgL2TP 5 }
-- L2TPv3 Client Mode END

-- ==================================
-- VLAN Tagging specific information
-- ==================================

tchRgVlan OBJECT IDENTIFIER ::=  { tchRg 11 }

tchRgVlanStripTagsWan OBJECT-TYPE
    SYNTAX      TruthValue
    MAX-ACCESS  read-write
    STATUS      current
    DESCRIPTION
        "This MIB only strips the VLAN tags for upstream traffic (toward the CMTS) from
        CPEs connected directly to the ethernet switch ports. Upstream traffic from CPEs
        connected to the wireless interfaces will NOT have the VLAN tags removed."
        DEFVAL { true }
    ::= {  tchRgVlan 1 }

tchRgVlanStripTagsLan OBJECT-TYPE
    SYNTAX      TruthValue
    MAX-ACCESS  read-write
    STATUS      current
    DESCRIPTION
        "This MIB only strips the VLAN tags for downstream traffic (toward the LAN) to
         CPEs connected directly to the ethernet switch ports. Downstream traffic to CPEs
         connected to the wireless interfaces will not have the VLAN tags removed."
    DEFVAL { true }
    ::= {  tchRgVlan 2 }


tchRgVlanTable OBJECT-TYPE
    SYNTAX      SEQUENCE OF TchRgVlanEntry
    MAX-ACCESS  not-accessible
    STATUS      current
    DESCRIPTION
        "This table contains information specific to VLANs."
    REFERENCE
        "CableHome 1.1 Specification,Packet Handling & Address
        Translation section."
    ::= {  tchRgVlan 3 }

tchRgVlanEntry OBJECT-TYPE
    SYNTAX      TchRgVlanEntry
    MAX-ACCESS  not-accessible
    STATUS      current
    DESCRIPTION
        "List of individual VLAN entries."
    INDEX { tchRgVlanID }
    ::= { tchRgVlanTable 1 }

TchRgVlanEntry ::= SEQUENCE {
    tchRgVlanID                      INTEGER,
    tchRgVlanDesc                        OCTET STRING,
    tchRgVlanEthernet            INTEGER,
    tchRgVlanWiFi                        INTEGER,
    tchRgVlanMoca                        INTEGER,
    tchRgVlanUSB                     INTEGER,
    tchRgVlanStartAddrType       InetAddressType,
    tchRgVlanStartAddr           InetAddress,
    tchRgVlanEndAddrType         InetAddressType,
    tchRgVlanEndAddr                 InetAddress,
    tchRgVlanSubnetMaskType      InetAddressType,
    tchRgVlanSubnetMask          InetAddress,
    tchRgVlanRouterIpType        InetAddressType,
    tchRgVlanRouterIp            InetAddress,
    tchRgVlanLeaseTime           INTEGER,
    tchRgVlanRouteMode           INTEGER,
    tchRgVlanTOS                     INTEGER,
    tchRgVlanFirewall            TruthValue,
    tchRgVlanUpnp                        TruthValue,
    tchRgVlanRowStatus           RowStatus
}

tchRgVlanID    OBJECT-TYPE
    SYNTAX    INTEGER   (2..1005)
    MAX-ACCESS  not-accessible
    STATUS      current
    DESCRIPTION
        "The ID of the VLAN Entry."
    ::= { tchRgVlanEntry 1 }

tchRgVlanDesc   OBJECT-TYPE
    SYNTAX OCTET STRING (SIZE(0..20))
    MAX-ACCESS read-write
    STATUS current
    DESCRIPTION
        "Description of this VLAN."
::= { tchRgVlanEntry 2 }

tchRgVlanEthernet    OBJECT-TYPE
    SYNTAX              INTEGER   (0..15)
    MAX-ACCESS  read-create
    STATUS      current
    DESCRIPTION
        "Assigns the Ethernet Port corresponding to the bit set to the VLAN.
         Bit 0 - Ethernet Port 1.
         Bit 1 - Ethernet Port 2.
         Bit 2 - Ethernet Port 3.
         Bit 3 - Ethernet Port 4."
    DEFVAL { 0 }
    ::= { tchRgVlanEntry 3 }

tchRgVlanWiFi    OBJECT-TYPE
    SYNTAX              INTEGER   (0..15)
    MAX-ACCESS  read-create
    STATUS      current
    DESCRIPTION
        "Assigns the WiFi BSSID corresponding to the bit set to the VLAN.
         Bit 0 - WiFi BSSID Port 0.
         Bit 1 - WiFi BSSID Port 1.
         Bit 2 - WiFi BSSID Port 2.
         Bit 3 - WiFi BSSID Port 3.
         ...
         Bit 15 - WiFi BSSID 15."
    DEFVAL { 0 }
    ::= { tchRgVlanEntry 4 }

tchRgVlanMoca    OBJECT-TYPE
    SYNTAX              INTEGER   (0..1)
    MAX-ACCESS  read-create
    STATUS      current
    DESCRIPTION
        "Include Moca on the VLAN."
    DEFVAL { 0 }
    ::= { tchRgVlanEntry 5 }

tchRgVlanUSB    OBJECT-TYPE
    SYNTAX              INTEGER   (0..1)
    MAX-ACCESS  read-create
    STATUS      current
    DESCRIPTION
        "Include USB on the VLAN."
    DEFVAL { 0 }
    ::= { tchRgVlanEntry 6 }

tchRgVlanStartAddrType OBJECT-TYPE
    SYNTAX      InetAddressType
    MAX-ACCESS  read-create
    STATUS      current
    DESCRIPTION
        "The start IP address range type."
    DEFVAL { ipv4 }
    ::= { tchRgVlanEntry 7 }

tchRgVlanStartAddr OBJECT-TYPE
    SYNTAX      InetAddress
    MAX-ACCESS  read-create
    STATUS      current
    DESCRIPTION
        "The start IP Address range."
    ::= { tchRgVlanEntry 8 }

tchRgVlanEndAddrType OBJECT-TYPE
    SYNTAX      InetAddressType
    MAX-ACCESS  read-create
    STATUS      current
    DESCRIPTION
        "The end IP address range type."
    DEFVAL { ipv4 }
    ::= { tchRgVlanEntry 9}

tchRgVlanEndAddr OBJECT-TYPE
    SYNTAX      InetAddress
    MAX-ACCESS  read-create
    STATUS      current
    DESCRIPTION
        "The end IP Address range."
    ::= { tchRgVlanEntry 10}


tchRgVlanSubnetMaskType OBJECT-TYPE
    SYNTAX      InetAddressType
    MAX-ACCESS  read-create
    STATUS      current
    DESCRIPTION
        "The subnet mask type."
    DEFVAL { ipv4 }
    ::= { tchRgVlanEntry 11}

tchRgVlanSubnetMask OBJECT-TYPE
    SYNTAX      InetAddress
    MAX-ACCESS  read-create
    STATUS      current
    DESCRIPTION
        "The subnet mask."
    ::= { tchRgVlanEntry 12}

tchRgVlanRouterIpType OBJECT-TYPE
    SYNTAX      InetAddressType
    MAX-ACCESS  read-create
    STATUS      current
    DESCRIPTION
        "The router IP type."
    DEFVAL { ipv4 }
    ::= { tchRgVlanEntry 13}

tchRgVlanRouterIp OBJECT-TYPE
    SYNTAX      InetAddress
    MAX-ACCESS  read-create
    STATUS      current
    DESCRIPTION
        "The router IP."
    ::= { tchRgVlanEntry 14}

tchRgVlanLeaseTime    OBJECT-TYPE
    SYNTAX              INTEGER
    MAX-ACCESS  read-create
    STATUS      current
    DESCRIPTION
        "The lease time for clients of this VLAN."
    DEFVAL { 3600 }
    ::= { tchRgVlanEntry 15}

tchRgVlanRouteMode    OBJECT-TYPE
    SYNTAX              INTEGER  {
          napt(1),
          bridged (2),
          routeddhcp(3)
          }
    MAX-ACCESS  read-create
    STATUS      current
    DESCRIPTION
        "The route mode for this VLAN.
        napt(1)   -- NAT with Port Translation Mode
        bridged (2)    -- Passthrough/Bridging Mode
        routeddhcp(3)  -- routed_dhcp"
    DEFVAL { 1 }
    ::= { tchRgVlanEntry 16}

tchRgVlanTOS    OBJECT-TYPE
    SYNTAX              INTEGER  (0..255)
    MAX-ACCESS  read-create
    STATUS      current
    DESCRIPTION
        "The Ethernet Frame TOS value for this VLAN."
    DEFVAL { 0 }
    ::= { tchRgVlanEntry 17}

tchRgVlanFirewall OBJECT-TYPE
    SYNTAX      TruthValue
    MAX-ACCESS  read-create
    STATUS      current
    DESCRIPTION
        "Include the firewall on this VLAN."
    DEFVAL { 1 }
    ::= { tchRgVlanEntry 18}

tchRgVlanUpnp OBJECT-TYPE
    SYNTAX      TruthValue
    MAX-ACCESS  read-create
    STATUS      current
    DESCRIPTION
        "Include the IGD UPnP on this VLAN."
    DEFVAL { true }
    ::= { tchRgVlanEntry 19}

tchRgVlanRowStatus OBJECT-TYPE
    SYNTAX      RowStatus
    MAX-ACCESS  read-create
    STATUS      current
    DESCRIPTION
          "The RowStatus interlock for the creation and deletion
        of a VLAN entry."
    ::= { tchRgVlanEntry 20}

tchRgVlanApplySettings OBJECT-TYPE
    SYNTAX      TruthValue
    MAX-ACCESS  read-write
    STATUS      current
    DESCRIPTION
        "If set to true(1), the current vlan MIB settings
         will be written to non-volatile storage and the VLAN Manager will
         re-initialize the networks using the new configuration.

         Unless this object is explicitly set to true(1), any settings made via
         other objects in this MIB will be lost if a reboot occurs.
         This MIB always returns false(2) when read."
    ::= {  tchRgVlan 4 }

-- ==================================
-- DS Lite specific information
-- ==================================

tchRgDslite OBJECT IDENTIFIER ::=  { tchRg 12 }

tchRgDsliteOption OBJECT-TYPE
    SYNTAX INTEGER {
                disable(0),
        option-64(1)
                }
    MAX-ACCESS  read-write
    STATUS      current
    DESCRIPTION
        "This MIB will toggle whether DHCPv6 option 64 is requested in the solicit.
                 The option should only be requested if DS Lite is enabled."
        DEFVAL { 1 }
    ::= {  tchRgDslite 1 }

tchRgDsliteAftrName OBJECT-TYPE
    SYNTAX SnmpAdminString
    MAX-ACCESS  read-write
    STATUS      current
    DESCRIPTION
        "This MIB will read/write the remote IPv6 FQDN of the AFTR router in
                 the DS Lite tunnel configuration.
                 This should only have an effect if eRouter is in IPv6 only mode and DS Lite is enabled."
    ::= {  tchRgDslite 2 }

tchRgDsliteAftrAddress OBJECT-TYPE
    SYNTAX InetAddressIPv6
    MAX-ACCESS  read-write
    STATUS      current
    DESCRIPTION
        "This MIB will set the remote IPv6 address of the AFTR router manually in
                 the DS Lite tunnel configuration.
                 This should only have an effect if eRouter is in IPv6 only mode and DS Lite is enabled."
    ::= {  tchRgDslite 3 }

tchRgDsliteTcpMssClamping OBJECT-TYPE
    SYNTAX      INTEGER (0..1420)
    MAX-ACCESS  read-write
    STATUS      current
    DESCRIPTION
        "Specifies  whether TCP MSS clamping is enabled on the interface.
         0 disables clamping, 1 clamps the MSS depending on the
         interface MTU. A value > 1 will be used as clamping size.
                 This MIB takes effect immediately and does not require tchRgDsliteApplySettings."
    DEFVAL { 0 }
    ::= { tchRgDslite 4 }

tchRgDsliteIPv4FragEnabled OBJECT-TYPE
    SYNTAX      TruthValue
    MAX-ACCESS  read-write
    STATUS      current
    DESCRIPTION
        "Enables or disable IPv4 fragmentation in DS-Lite.
                This MIB takes effect immediately and does not require tchRgDsliteApplySettings."
    DEFVAL { false }
::= { tchRgDslite 5 }

tchRgDslitePcpMode OBJECT-TYPE
    SYNTAX      TruthValue
    MAX-ACCESS  read-write
    STATUS      current
    DESCRIPTION
        "This MIB controls the PCP operation mode for DS-Lite.
                False: plain mode, our client will not accept port-mapping messages from a PCP server.
                True: encapsulation mode, our client will accept port-mapping messages from a PCP server.
                "
    DEFVAL { false }
::= { tchRgDslite 6 }



tchRgDsliteEndpointAssignmentPrecedence OBJECT-TYPE
     SYNTAX INTEGER {
                Static(0),
        DHCPv6(1)
                }
    MAX-ACCESS  read-write
    STATUS      current
    DESCRIPTION
        "This MIB controls the precedence mode for DS-Lite.
                Static: the aftr adress will be give statically using the parameter tchRgDsliteAftrAddress or tchRgDsliteAftrName.
                DHCPv6: the aftr adress will be resolved after get the aftr name from option 64
                "
    DEFVAL { DHCPv6 }
::= { tchRgDslite 8 }

tchRgDsliteEndpointAddressTypePrecedence OBJECT-TYPE
    SYNTAX INTEGER {
                FDQN(0),
        IPv6Address(1)
                }
    MAX-ACCESS  read-write
    STATUS      current
    DESCRIPTION
        "This MIB controls the type of precedence mode for DS-Lite.    
                FQDN: the name of the aftr will be use
                IPv6Address: the ipv6 adress will be use
                "
    DEFVAL { 0 }
::= { tchRgDslite 9 }

tchRgDsliteApplySettings OBJECT-TYPE
    SYNTAX      TruthValue
    MAX-ACCESS  read-write
    STATUS      current
    DESCRIPTION
        "If set to true(1), then all the settings (MIB values)
         from this MIB tree will be applied to the runtime configuration,
         This will resolve the AFTR domain name to the AFTR IPv6 address,
                 and initialize the DSlite tunnel. This will initialize using the AFTR
                 address if both the address and FQDN are defined.
                 This should only activate the tunnel if eRouter is in IPv6 only mode
                 and DS Lite is enabled.
         Always returns false(2) when read."
    ::= { tchRgDslite 1001 }

-- ==================================
-- Wifi Hotspot Specific Information
-- ==================================

tchRgWifiHotspotMib OBJECT IDENTIFIER ::= { tchRg 13 }

tchRgWifiHotspotBase OBJECT IDENTIFIER ::= { tchRgWifiHotspotMib 1 }

tchRgWifiHotspotEnabled OBJECT-TYPE
    SYNTAX      TruthValue
    MAX-ACCESS  read-write
    STATUS      current
    DESCRIPTION
        "Enables or disable Wifi Hotspot support in the device."
   ::= { tchRgWifiHotspotBase 1 }

tchRgWifiHotspotTable OBJECT-TYPE
    SYNTAX      SEQUENCE OF TchRgWifiHotspotEntry
    MAX-ACCESS  not-accessible
    STATUS      current
    DESCRIPTION
        "A table used to configure settings related to Wi-fi Hotspot."
    ::= { tchRgWifiHotspotBase 2 }

tchRgWifiHotspotEntry OBJECT-TYPE
    SYNTAX      TchRgWifiHotspotEntry
    MAX-ACCESS  not-accessible
    STATUS      current
    DESCRIPTION
         "An entry defining the Wi-fi hotspot characteristics of an
          individual Wi-Fi network interface."
    INDEX   { tchRgWifiHotspotIf }
    ::= { tchRgWifiHotspotTable 1 }

TchRgWifiHotspotEntry ::=
    SEQUENCE    {
        tchRgWifiHotspotInstance              Unsigned32,
        tchRgWifiHotspotIf                    INTEGER,
        tchRgWifiHotspotMode                  INTEGER,
        tchRgWifiHotspotCpeIdleTimeout        Unsigned32,
        tchRgWifiHotspotCpeSessionTimeout     Unsigned32,
        tchRgWifiHotspotRadiusAccAddressType  InetAddressType,
        tchRgWifiHotspotRadiusAccAddress      InetAddress,
        tchRgWifiHotspotRadiusAccPort         InetPortNumber,
        tchRgWifiHotspotRadiusAccKey          DisplayString,
        tchRgWifiHotspotPacketFilterMask      Unsigned32,
        tchRgWifiHotspotInsertDhcpOptionsMask Unsigned32,
        tchRgWifiHotspotRowStatus             RowStatus,
        tchRgWifiHotspotRadiusAccInterimInterval Unsigned32
    }


tchRgWifiHotspotInstance    OBJECT-TYPE
    SYNTAX      Unsigned32
    MAX-ACCESS  not-accessible
    STATUS      current
    DESCRIPTION
        "The key for a unique instance of this object."
    ::= { tchRgWifiHotspotEntry 1 }

tchRgWifiHotspotIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Wi-fi network interface."
    ::= { tchRgWifiHotspotEntry 2 }

tchRgWifiHotspotMode OBJECT-TYPE
    SYNTAX      INTEGER {
                disable(1),
                enableBridge(2),
                enableL2oGre(3)
    }
    MAX-ACCESS  read-create
    STATUS      current
    DESCRIPTION
        "Wi-fi Hotsot mode:
         enableBridge - Wi-Fi traffic will be bridged
         enableL2oGre - Wi-Fi traffic will be sent over GRE tunnel.
                        GRE Tunnel should be configured and enabled."
    ::= { tchRgWifiHotspotEntry 3 }

tchRgWifiHotspotCpeIdleTimeout OBJECT-TYPE
    SYNTAX      Unsigned32
    MAX-ACCESS  read-create
    STATUS      current
    DESCRIPTION
        "CPE inactivity/idle timeout in seconds which will trigger disconnect.
         Value of 0 will disable inactivity tracking."
    ::= { tchRgWifiHotspotEntry 4 }

tchRgWifiHotspotCpeSessionTimeout OBJECT-TYPE
    SYNTAX      Unsigned32
    MAX-ACCESS  read-create
    STATUS      current
    DESCRIPTION
        "CPE maximum session duration timeout in seconds.
         Value of 0 will disable tracking session duration."
    ::= { tchRgWifiHotspotEntry 5 }

tchRgWifiHotspotRadiusAccAddressType OBJECT-TYPE
    SYNTAX      InetAddressType
    MAX-ACCESS  read-create
    STATUS      current
    DESCRIPTION
        "The type of internet address used for tchRgWifiHotspotRadiusAccAddress."
    ::= { tchRgWifiHotspotEntry 6 }

tchRgWifiHotspotRadiusAccAddress OBJECT-TYPE
    SYNTAX      InetAddress
    MAX-ACCESS  read-create
    STATUS      current
    DESCRIPTION
        "The internet address of the RADIUS Accounting server for this service set."
    ::= { tchRgWifiHotspotEntry 7 }

tchRgWifiHotspotRadiusAccPort OBJECT-TYPE
    SYNTAX      InetPortNumber
    MAX-ACCESS  read-create
    STATUS      current
    DESCRIPTION
        "The UDP port used to communicate with the RADIUS Accounting server.
         Default value set to 1813."
    DEFVAL { 1813 }
    ::= { tchRgWifiHotspotEntry 8 }

tchRgWifiHotspotRadiusAccKey OBJECT-TYPE
    SYNTAX      DisplayString
    MAX-ACCESS  read-create
    STATUS      current
    DESCRIPTION
        "The RADIUS Accounting server shared security key."
    ::= { tchRgWifiHotspotEntry 9 }

tchRgWifiHotspotPacketFilterMask OBJECT-TYPE
    SYNTAX      Unsigned32
    MAX-ACCESS  read-create
    STATUS      current
    DESCRIPTION
        "Bit mask for limiting traffic to certain packet types.
         Possible value:
         11111111 11111111 11111111 11111111: Allow All traffic
         xxxxxxxx xxxxxxxx xxxxxxxx xxxxxxx1: Allow IPv4 (0x0800) packets
         xxxxxxxx xxxxxxxx xxxxxxxx xxxxxx1x: Allow IPv6 (0x86dd) packets
         xxxxxxxx xxxxxxxx xxxxxxxx xxxxx1xx: Allow IPx  (0x8137) packets
         xxxxxxxx xxxxxxxx xxxxxxxx xxxx1xxx: Allow ARP  (0x0806) packets
         xxxxxxxx xxxxxxxx xxxxxxxx xxx1xxxx: Allow RARP (0x8035) packets
         xxxxxxxx xxxxxxxx xxxxxxxx xx1xxxxx: Allow VLAN (0x8100) packets
         "
    ::= { tchRgWifiHotspotEntry 10 }

tchRgWifiHotspotInsertDhcpOptionsMask OBJECT-TYPE
    SYNTAX      Unsigned32
    MAX-ACCESS  read-create
    STATUS      current
    DESCRIPTION
        "Bit mask for inserting DHCP options in DHCP Discover/Request packet from
         connected wifi client device.
         Possible value:
         0x1: Insert DHCP relay agent option 82.
              circuit-id sub-option: AP-MAC-ADDRESS;SSID-NAME;SSID-TYPE
         0x2: Insert DHCP relay agent option 82.
              remote-id  sub-option: String containing MAC address of connected
                                     wifi client device in the format XX:XX:XX:XX:XX:XX.
         0x4:   Insert/Modify DHCP option 60 with string containing SSID Name.
         0x8:   Enables/Disables CM MAC address (format XX:XX:XX:XX:XX:XX) included in DHCP option 82.2 remote-id
         0x100: if DCHP relay agent option 82 is present, changes the delimeter from semicolon, (;), to '0x00'.
         0x200: if DCHP relay agent option 82 is present, and SSID is open, append '0'. If it is closed append '1'."
    ::= { tchRgWifiHotspotEntry 11 }

tchRgWifiHotspotRowStatus OBJECT-TYPE
    SYNTAX RowStatus
    MAX-ACCESS read-create
    STATUS current
    DESCRIPTION
        "The RowStatus interlock for the creation and deletion
        can be modified at any time while the row is active(1)."
    ::= { tchRgWifiHotspotEntry 12 }

tchRgWifiHotspotRadiusAccInterimInterval OBJECT-TYPE 
    SYNTAX      Unsigned32 
    MAX-ACCESS  read-create 
    STATUS      current 
    DESCRIPTION 
              "Setting to control interval between each RADIUS interim update in seconds. 
              Feature may be disabled by setting to zero, else minimum value is 60" 
    DEFVAL { 900 }
    ::= { tchRgWifiHotspotEntry 13 }

tchRgWifiHotspotAutRateLimit OBJECT-TYPE
    SYNTAX      Unsigned32
    MAX-ACCESS  read-write
    STATUS      current
    DESCRIPTION
        "Authentication rate limit in messages per second. If client exceeds
         this limit, authentication from the client is ignored for
         tchRgWifiHotspotAutDenialTimeout."
   ::= { tchRgWifiHotspotBase 3 }

tchRgWifiHotspotAutDenialTimeout OBJECT-TYPE
    SYNTAX      Unsigned32
    MAX-ACCESS  read-write
    STATUS      current
    DESCRIPTION
        "Timeout in seconds during which authentication from a client is ignored
         once authentication message rate exceeds tchRgWifiHotspotAutRateLimit."
   ::= { tchRgWifiHotspotBase 4 }

tchRgWifiHotspotRadiusOrigIf OBJECT-TYPE
    SYNTAX      INTEGER {
                eRouter(1),
                cm(2)
        }
    MAX-ACCESS  read-write
    STATUS      current
    DESCRIPTION
        "Originating interface of radius authentication and accounting traffic."
    ::= { tchRgWifiHotspotBase 5 }

tchRgWifiHotspotIgnoreMaxCpeSetting OBJECT-TYPE
    SYNTAX      TruthValue
    MAX-ACCESS  read-write
    STATUS      current
    DESCRIPTION
        "This setting is applicable for wifi hotspot bridged mode.
         When set to true(1), clients connected through the hotspot wifi will not be
         counted when enforcing the 'Maximum CPE devices' on DOCSIS."
   ::= { tchRgWifiHotspotBase 6 }

tchRgWifiHotspotCapable OBJECT-TYPE
    SYNTAX      TruthValue
    MAX-ACCESS  read-write
    STATUS      current
    DESCRIPTION
        "Returns whether the device is capable of WiFi HotSpot functionality."
   ::= { tchRgWifiHotspotBase 7 }

tchRgWifiHotspotConnectedClientsTable OBJECT-TYPE
    SYNTAX      SEQUENCE OF TchRgWifiHotspotConnectedClientsEntry
    MAX-ACCESS  not-accessible
    STATUS      current
    DESCRIPTION
        "Clients table connected to Wi-fi Hotspot."
    ::= { tchRgWifiHotspotBase 8 }

tchRgWifiHotspotConnectedClientsEntry OBJECT-TYPE
    SYNTAX      TchRgWifiHotspotConnectedClientsEntry
    MAX-ACCESS  not-accessible
    STATUS      current
    DESCRIPTION
         "An entry defining the Wi-fi hotspot connected clients"
    INDEX   { tchRgWifiHotspotIf, tchRgWifiHotspotConnectedClientsIndex }
    ::= { tchRgWifiHotspotConnectedClientsTable 1 }

TchRgWifiHotspotConnectedClientsEntry ::=
    SEQUENCE    {
        tchRgWifiHotspotConnectedClientsIndex              INTEGER,
                tchRgWifiHotspotConnectedClientsPhysAddr                   PhysAddress,
        tchRgWifiHotspotConnectedClientsRssiLevel          Integer32,
                tchRgWifiHotspotConnectedClientsIpv4Addr                   IpAddress,
                tchRgWifiHotspotConnectedClientsHostName           SnmpAdminString,
                tchRgWifiHotspotConnectedClientsDhcpv4Status               INTEGER
    }

tchRgWifiHotspotConnectedClientsIndex    OBJECT-TYPE
    SYNTAX      INTEGER (0..127)
    MAX-ACCESS  not-accessible
    STATUS      current
    DESCRIPTION
        "The index of the client connected to specific hotspot ssid."
    ::= { tchRgWifiHotspotConnectedClientsEntry 1 }

tchRgWifiHotspotConnectedClientsPhysAddr OBJECT-TYPE
    SYNTAX      PhysAddress
    MAX-ACCESS  read-only
    STATUS      current
    DESCRIPTION
            "MAC address of the client connected to the Hotspot SSID"
    ::= { tchRgWifiHotspotConnectedClientsEntry 2 }

tchRgWifiHotspotConnectedClientsRssiLevel OBJECT-TYPE
    SYNTAX      Integer32
    MAX-ACCESS  read-only
    STATUS      current
    DESCRIPTION
            "Signal strength of the Hotspot client in dBm"
    ::= { tchRgWifiHotspotConnectedClientsEntry 3 }

tchRgWifiHotspotConnectedClientsIpv4Addr OBJECT-TYPE
    SYNTAX      IpAddress
    MAX-ACCESS  read-only
    STATUS      current
    DESCRIPTION
            "IPv4 address obtained by the client from Hotspot DHCP server"
    ::= { tchRgWifiHotspotConnectedClientsEntry 4 }

tchRgWifiHotspotConnectedClientsHostName OBJECT-TYPE
    SYNTAX      SnmpAdminString
    MAX-ACCESS  read-only
    STATUS      current
    DESCRIPTION
            "Hostname of the client based on DHCP option 12."
    ::= { tchRgWifiHotspotConnectedClientsEntry 5 }

tchRgWifiHotspotConnectedClientsDhcpv4Status OBJECT-TYPE
    SYNTAX      INTEGER  {
                                        discover(1),
                                        offer(2),
                                        request(3),
                                        ack(4),
                                        nack(5)
                        }
    MAX-ACCESS  read-only
    STATUS      current
    DESCRIPTION
            "DHCPv4 status of the Hotspot client."
    ::= { tchRgWifiHotspotConnectedClientsEntry 6 }

tchRgWifiHotspotDisablePMKCaching OBJECT-TYPE     
    SYNTAX      TruthValue
    MAX-ACCESS  read-write
    STATUS      current
    DESCRIPTION
        "Enables or disable WPA2 PMK Caching. By default this feature is enable"
    DEFVAL { true }
   ::= { tchRgWifiHotspotBase 9 }

tchRgWifiHotspotConnectionSpeedMin OBJECT-TYPE     
    SYNTAX      Unsigned32
    MAX-ACCESS  read-write
    STATUS      current
    DESCRIPTION
        "Minimum connection speed in kbps required by client to maintain connectivity."
   ::= { tchRgWifiHotspotBase 10 }

tchRgWifiHotspotConnectionSpeedTimeout OBJECT-TYPE     
    SYNTAX      Unsigned32
    MAX-ACCESS  read-write
    STATUS      current
    DESCRIPTION
        "Timeout in seconds during which client is allowed to maintain connectivity
         once connection speed is below tchRgWifiHotspotConnectionSpeedMin. When timeout
         expires client is disassociated."
   ::= { tchRgWifiHotspotBase 11 }
   
tchRgWifiHotspotProtect OBJECT-TYPE     
    SYNTAX      INTEGER {
                enabled(1),
                disabled(2),
                disabledAndclear(3),
                enabledAndclear(4)
        }
    MAX-ACCESS  read-write
    STATUS      current
    DESCRIPTION
        "Enable or disable automated ACL filling and possibly clear ACL list.
        Returns solely enabled(1) or disabled(2) when read."
    DEFVAL { 2 }
    ::= { tchRgWifiHotspotBase 12 }

-- ====================================================
-- L2oGRE tunnel for Wifi Hotspot specific information
-- ====================================================

tchRgL2ogreMib OBJECT IDENTIFIER ::= { tchRg 14 }

tchRgL2ogreBase OBJECT IDENTIFIER ::= { tchRgL2ogreMib 1 }

tchRgL2ogreEnabled OBJECT-TYPE
    SYNTAX      TruthValue
    MAX-ACCESS  read-write
    STATUS      current
    DESCRIPTION
        "Enables or disable GRE Tunnel support in the device."
    DEFVAL { false }
   ::= { tchRgL2ogreBase 1 }

tchRgL2ogrePriRemoteAddressType OBJECT-TYPE
    SYNTAX      InetAddressType
    MAX-ACCESS  read-write
    STATUS      current
    DESCRIPTION
        "The IP address type (ipv4, ipv6 or dns) of primary remote
         endpoint of the GRE tunnel."
    DEFVAL { ipv4 }
    ::= { tchRgL2ogreBase 2 }

tchRgL2ogrePriRemoteAddress OBJECT-TYPE
    SYNTAX      InetAddress
    MAX-ACCESS  read-write
    STATUS      current
    DESCRIPTION
        "IP address or FQDN of primary remote endpoint of the GRE tunnel."
    ::= { tchRgL2ogreBase 3 }

tchRgL2ogreSecRemoteAddressType OBJECT-TYPE
    SYNTAX      InetAddressType
    MAX-ACCESS  read-write
    STATUS      current
    DESCRIPTION
        "The IP address type (ipv4, ipv6 or dns) of secondary remote
         endpoint of the GRE tunnel."
    DEFVAL { ipv4 }
    ::= { tchRgL2ogreBase 4 }

tchRgL2ogreSecRemoteAddress OBJECT-TYPE
    SYNTAX      InetAddress
    MAX-ACCESS  read-write
    STATUS      current
    DESCRIPTION
        "IP address or FQDN of secondary remote endpoint of the GRE tunnel."
    ::= { tchRgL2ogreBase 5 }

tchRgL2ogreDSCP OBJECT-TYPE
    SYNTAX      Integer32 (0..63)
    MAX-ACCESS  read-write
    STATUS      current
    DESCRIPTION
        "The method is used to set the high 6 bits of TOS in the
         IPv4 header or traffic class in IPv6 header."
    ::= { tchRgL2ogreBase 6 }

tchRgL2ogreKeepAliveMode OBJECT-TYPE
    SYNTAX      INTEGER {
                disabled(1),
                ping(2),
                ping-noswitchover(3)
    }
    MAX-ACCESS  read-write
    STATUS      current
    DESCRIPTION
        "Keepalive modes for failover mechanism.
         ping - Use ICMP pings within tunnel as a keepalive messages."
    ::= { tchRgL2ogreBase 7 }

tchRgL2ogreKeepAliveCount OBJECT-TYPE
    SYNTAX      Integer32
    MAX-ACCESS  read-write
    STATUS      current
    DESCRIPTION
        "Number of keep-alive messages sent at regular interval."
    ::= { tchRgL2ogreBase 8 }

tchRgL2ogreKeepAliveInterval OBJECT-TYPE
    SYNTAX      Integer32
    MAX-ACCESS  read-write
    STATUS      current
    DESCRIPTION
        "Interval in seconds between keep-alive messages."
    ::= { tchRgL2ogreBase 9 }

tchRgL2ogreKeepAliveFailureThreshold OBJECT-TYPE
    SYNTAX      Integer32
    MAX-ACCESS  read-write
    STATUS      current
    DESCRIPTION
        "Number of keep-alive failures that will cause fail-over."
    ::= { tchRgL2ogreBase 10 }

tchRgL2ogreStatsTable OBJECT-TYPE
    SYNTAX      SEQUENCE OF TchRgL2ogreStatsEntry
    MAX-ACCESS  not-accessible
    STATUS      current
    DESCRIPTION
        "This table provides statistical information of GRE tunnel."
    ::= { tchRgL2ogreBase 11 }

tchRgL2ogreStatsEntry OBJECT-TYPE
    SYNTAX      TchRgL2ogreStatsEntry
    MAX-ACCESS  not-accessible
    STATUS      current
    DESCRIPTION
        "This table provides statistical information of GRE tunnel."
    INDEX { tchRgL2ogreStatsIndex }
    ::= { tchRgL2ogreStatsTable 1 }

TchRgL2ogreStatsEntry ::= SEQUENCE {
    tchRgL2ogreStatsIndex                    Integer32,
    tchRgL2ogreStatsBytesSent                Counter64,
    tchRgL2ogreStatsBytesReceived            Counter64,
    tchRgL2ogreStatsPacketsSent              Counter64,
    tchRgL2ogreStatsPacketsReceived          Counter64,
    tchRgL2ogreStatsDiscardPacketsReceived   Counter64,
    tchRgL2ogreStatsErrorPacketsReceived     Counter64,
    tchRgL2ogreStatsKeepAliveSent            Counter64,
    tchRgL2ogreStatsKeepAliveReceived        Counter64,
    tchRgL2ogreStatsRowStatus                RowStatus
}

tchRgL2ogreStatsIndex OBJECT-TYPE
    SYNTAX      Integer32 (1..256)
    MAX-ACCESS  not-accessible
    STATUS      current
    DESCRIPTION
        "Table index"
    ::= { tchRgL2ogreStatsEntry 1 }

tchRgL2ogreStatsBytesSent OBJECT-TYPE
    SYNTAX      Counter64
    MAX-ACCESS  read-only
    STATUS      current
    DESCRIPTION
        "Number bytes sent."
    ::= { tchRgL2ogreStatsEntry 2 }

tchRgL2ogreStatsBytesReceived OBJECT-TYPE
    SYNTAX      Counter64
    MAX-ACCESS  read-only
    STATUS      current
    DESCRIPTION
        "Number bytes received."
    ::= { tchRgL2ogreStatsEntry 3 }

tchRgL2ogreStatsPacketsSent OBJECT-TYPE
    SYNTAX      Counter64
    MAX-ACCESS  read-only
    STATUS      current
    DESCRIPTION
        "Number packets sent."
    ::= { tchRgL2ogreStatsEntry 4 }

tchRgL2ogreStatsPacketsReceived OBJECT-TYPE
    SYNTAX      Counter64
    MAX-ACCESS  read-only
    STATUS      current
    DESCRIPTION
        "Number packets received."
    ::= { tchRgL2ogreStatsEntry 5 }

tchRgL2ogreStatsDiscardPacketsReceived OBJECT-TYPE
    SYNTAX      Counter64
    MAX-ACCESS  read-only
    STATUS      current
    DESCRIPTION
        "Number packets received that were discarded.
         Because source network interface is down."
    ::= { tchRgL2ogreStatsEntry 6 }

tchRgL2ogreStatsErrorPacketsReceived OBJECT-TYPE
    SYNTAX      Counter64
    MAX-ACCESS  read-only
    STATUS      current
    DESCRIPTION
        "Number packets received that were in error.
         Because tunnel packets are not correct type.
         Eg. Received IP packet instead of L2 packets."
    ::= { tchRgL2ogreStatsEntry 7 }

tchRgL2ogreStatsKeepAliveSent OBJECT-TYPE
    SYNTAX      Counter64
    MAX-ACCESS  read-only
    STATUS      current
    DESCRIPTION
        "Number keepalive packets sent."
    ::= { tchRgL2ogreStatsEntry 8 }

tchRgL2ogreStatsKeepAliveReceived OBJECT-TYPE
    SYNTAX      Counter64
    MAX-ACCESS  read-only
    STATUS      current
    DESCRIPTION
        "Number keepalive packets received."
    ::= { tchRgL2ogreStatsEntry 9 }

tchRgL2ogreStatsRowStatus OBJECT-TYPE
    SYNTAX      RowStatus
    MAX-ACCESS  read-create
    STATUS      current
    DESCRIPTION
        "The RowStatus interlock for the creation and deletion of a table entry."
    ::= { tchRgL2ogreStatsEntry 10 }

tchRgL2ogreSourceIfTable OBJECT-TYPE
    SYNTAX      SEQUENCE OF TchRgL2ogreSourceIfEntry
    MAX-ACCESS  not-accessible
    STATUS      current
    DESCRIPTION
        "This table contains information specific to network source interface
         whose traffic is mapped into GRE tunnel."
    ::= { tchRgL2ogreBase 12 }

tchRgL2ogreSourceIfEntry OBJECT-TYPE
    SYNTAX      TchRgL2ogreSourceIfEntry
    MAX-ACCESS  not-accessible
    STATUS      current
    DESCRIPTION
        "List of individual source interface entries mapped into GRE tunnel."
    INDEX { tchRgL2ogreSourceIfInstance }
    ::= { tchRgL2ogreSourceIfTable 1 }

TchRgL2ogreSourceIfEntry ::= SEQUENCE {
    tchRgL2ogreSourceIfInstance           Unsigned32,
    tchRgL2ogreSourceIf                   INTEGER,
    tchRgL2ogreSourceIfEnabled            TruthValue,
    tchRgL2ogreSourceIfVlanTag            Integer32,
    tchRgL2ogreSourceIfMplsHeader         Integer32,
    tchRgL2ogreSourceIfRowStatus          RowStatus
}

tchRgL2ogreSourceIfInstance    OBJECT-TYPE
    SYNTAX      Unsigned32
    MAX-ACCESS  not-accessible
    STATUS      current
    DESCRIPTION
        "The key for a unique instance of this object."
    ::= {tchRgL2ogreSourceIfEntry 1 }

tchRgL2ogreSourceIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Source interface whose traffic will be pass through GRE tunnel."
    ::= { tchRgL2ogreSourceIfEntry 2 }

tchRgL2ogreSourceIfEnabled OBJECT-TYPE
    SYNTAX      TruthValue
    MAX-ACCESS  read-create
    STATUS      current
    DESCRIPTION
        "Enables or disable mapping traffic from network interface into GRE tunnel."
   ::= { tchRgL2ogreSourceIfEntry 3 }

tchRgL2ogreSourceIfVlanTag OBJECT-TYPE
    SYNTAX      Integer32
    MAX-ACCESS  read-create
    STATUS      current
    DESCRIPTION
        "Add VLAN tag consists of 16bit of Tag Protocol Identifier (TPID)
         and 16 bit of Tag Control Identifier (TCI).
         Value of 0 will disable adding VLAN tag.
         Tag Protocol Identifier (TPID) should set to 0x8100."
    ::= { tchRgL2ogreSourceIfEntry 4 }

tchRgL2ogreSourceIfMplsHeader OBJECT-TYPE
    SYNTAX      Integer32
    MAX-ACCESS  read-create
    STATUS      current
    DESCRIPTION
        "MPLS Header. Value of 0 will disable adding MPLS Header."
    ::= { tchRgL2ogreSourceIfEntry 5 }

tchRgL2ogreSourceIfRowStatus OBJECT-TYPE
    SYNTAX      RowStatus
    MAX-ACCESS  read-create
    STATUS      current
    DESCRIPTION
        "The RowStatus interlock for the creation and deletion of a table entry."
    ::= { tchRgL2ogreSourceIfEntry 6 }

tchRgL2ogreOrigIf OBJECT-TYPE
    SYNTAX      INTEGER {
                eRouter(1),
				cM(2)
               }
    MAX-ACCESS  read-write
    STATUS      current
    DESCRIPTION
        "Originating Interface of GRE tunnel."
    ::= { tchRgL2ogreBase 13 }

tchRgL2ogreConcentratorServiceName OBJECT-TYPE
    SYNTAX      DisplayString
    MAX-ACCESS  read-write
    STATUS      current
    DESCRIPTION
        "FQDN of GRE tunnel concentrator/gw service.
         If this is set then, DNS Query of type SRV will be used for discovering
         FQDN of primary and secondary remote endpoint of GRE tunnel."
    ::= { tchRgL2ogreBase 14 }

tchRgL2ogreDnsResolverRetryTimerMin OBJECT-TYPE
    SYNTAX      Unsigned32
    MAX-ACCESS  read-write
    STATUS      current
    DESCRIPTION
        "Minimum timeout interval in seconds before retrying DNS query."
    ::= { tchRgL2ogreBase 15 }

tchRgL2ogreDnsResolverRetryTimerMax OBJECT-TYPE
    SYNTAX      Unsigned32
    MAX-ACCESS  read-write
    STATUS      current
    DESCRIPTION
        "Maximum timeout interval in seconds before retrying DNS query."
    ::= { tchRgL2ogreBase 16 }

tchRgL2ogreKeepAliveFailureInterval OBJECT-TYPE
    SYNTAX      Integer32
    MAX-ACCESS  read-write
    STATUS      current
    DESCRIPTION
        "Configured interval between pings for WLAN GW when disabled due to both WLAN GWs failing."
    ::= { tchRgL2ogreBase 17 }

tchRgL2ogreKeepAliveReattemptInterval OBJECT-TYPE
    SYNTAX      Integer32
    MAX-ACCESS  read-write
    STATUS      current
    DESCRIPTION
        "Configured interval to reattempt connection to a primary WLAN GW even when secondary WLAN GW is available and clients are connected."
    ::= { tchRgL2ogreBase 18 }

tchRgL2ogreTcpMssClamping OBJECT-TYPE
    SYNTAX      INTEGER (0..1420)
    MAX-ACCESS  read-write
    STATUS      current
    DESCRIPTION
        "Specifies  whether TCP MSS clamping is enabled on the interface. 
         0 disables clamping, 1 clamps the MSS depending on the 
         interface MTU. A value > 1 will be used as clamping size."
    DEFVAL { 0 }
    ::= { tchRgL2ogreBase 19 }
    
tchRgL2ogrePriRemoteAddressResolvedType OBJECT-TYPE
    SYNTAX      InetAddressType
    MAX-ACCESS  read-write
    STATUS      current
    DESCRIPTION
        "The IP address type (ipv4 or ipv6) of resolved FQDN of
         GRE tunnel endpoint."
    DEFVAL { ipv4 }
    ::= { tchRgL2ogreBase 20 }

tchRgL2ogrePriRemoteResolvedAddress OBJECT-TYPE
    SYNTAX      InetAddress
    MAX-ACCESS  read-write
    STATUS      current
    DESCRIPTION
        "IP address, v4 or v6, when tchRgL2ogrePriRemoteAddress is filled with FQDN."
    ::= { tchRgL2ogreBase 21 }

tchRgL2ogreSecRemoteAddressResolvedType OBJECT-TYPE
    SYNTAX      InetAddressType
    MAX-ACCESS  read-write
    STATUS      current
    DESCRIPTION
        "The IP address type (ipv4 or ipv6) of resolved FQDN of
         GRE tunnel endpoint."
    DEFVAL { ipv4 }
    ::= { tchRgL2ogreBase 22 }

tchRgL2ogreSecRemoteResolvedAddress OBJECT-TYPE
    SYNTAX      InetAddress
    MAX-ACCESS  read-write
    STATUS      current
    DESCRIPTION
        "IP address, v4 or v6, when tchRgL2ogreSecRemoteAddress is filled with FQDN."
    ::= { tchRgL2ogreBase 23 }

tchRgIGMP OBJECT IDENTIFIER ::= { tchRg 15 }

tchRgIGMPMaxRspTime OBJECT-TYPE
    SYNTAX INTEGER {
        igmpV2(1),
        igmpV3(2)
        }
    MAX-ACCESS  read-write
    STATUS      current
    DESCRIPTION
        "There is a difference in IGMPv2 and IGMPv3 to translate the MAX RSP CODE to MAX RSP TIME.
                 In IGMPv2 MAX RSP TIME = MAX RSP CODE/10.
                 In IGMPv3, When Max RSP Code > 128, max response time is calculated differently.
                 When this MIB is set to IGMPv2(1) modem will set max response time according to IGMPv2 standard.
                 This setting is recommended for older CMTS implementations and when random response time of 0 to 10 sec is desired.
                 When this MIB is set to IGMPv3(2) modem will set max response time according to IGMPv3 standard.
                 This setting is recommended for new CMTS implementations and when random response time of 0 to above 10 seconds is desired.
         This object is stored in non-vol and defaults to IGMPv2(1) after factory reset."
        DEFVAL { 1 }
    ::= { tchRgIGMP 1 }

tchRgIGMPTransferFeature OBJECT-TYPE
    SYNTAX INTEGER {
        disable(0),
        enable(1)
        }
    MAX-ACCESS  read-write
    STATUS      current
    DESCRIPTION
        "0: Disable, IGMP transfer feature (IGMPv2 transfer to IGMPv3) is disable.
		 1: Enable, IGMP transfer feature (IGMPv2 transfer to IGMPv3) is enable."
        DEFVAL { 0 }
    ::= { tchRgIGMP 2 }

tchRgIGMPVersion OBJECT-TYPE
    SYNTAX  INTEGER {
        igmpv2Igmpv3(0),
        igmpv3Only(1),
        igmpv2Only(2)
        }
    MAX-ACCESS  read-write
    STATUS      current
    DESCRIPTION
        "0: IGMPv2 and IGMPv3.
         1: IGMPv3 only.
         2: IGMPv2 only."
    DEFVAL { igmpv2Igmpv3 }
    ::= { tchRgIGMP 3 }

tchRgIGMPEnable OBJECT-TYPE
    SYNTAX      TruthValue
    MAX-ACCESS  read-write
    STATUS      current
    DESCRIPTION
        "Enable/Disable IGMP feature "
    DEFVAL { true }
    ::= { tchRgIGMP 4 }

tchRgIGMPMaxSessions OBJECT-TYPE
    SYNTAX      Unsigned32 (1..50)
    MAX-ACCESS  read-write
    STATUS      current
    DESCRIPTION
         "This MIB will restrict the maximum number of concurrent IGMP Multicast sessions for a unique Multicast group.
	 The minimum value is 1 session and the maximum value is 50 sessions, the factory default value is 30 sessions."
    DEFVAL { 30}
    ::= { tchRgIGMP 5 }

-- ====================================================
-- Network Extender Status MIB
-- ====================================================

tchRgNetworkExtenders OBJECT IDENTIFIER ::= { tchRg 16 }

tchRgNetworkExtenderTable  OBJECT-TYPE
    SYNTAX      SEQUENCE OF TchRgNetworkExtenderEntry
    MAX-ACCESS  not-accessible
    STATUS      current
    DESCRIPTION
        "Multiple Attached Network Extender Table. Maximum of 8 Entries"

    ::= { tchRgNetworkExtenders 1 }

tchRgNetworkExtenderEntry OBJECT-TYPE
    SYNTAX      TchRgNetworkExtenderEntry
    MAX-ACCESS  not-accessible
    STATUS      current
    DESCRIPTION
        "A row in the table which represents information about attached Network Extender."
    INDEX   { tchRgNetworkExtenderIndex }
    ::= { tchRgNetworkExtenderTable 1 }

TchRgNetworkExtenderEntry ::= SEQUENCE {
      tchRgNetworkExtenderIndex                INTEGER,
      tchRgNetworkExtenderIpAddress            IpAddress,
      tchRgNetworkExtenderDeviceName           OCTET STRING,
      tchRgNetworkExtenderVenderName           OCTET STRING,
      tchRgNetworkExtenderModelNumber          OCTET STRING,
      tchRgNetworkExtenderFirmwareVersion      OCTET STRING
    }

tchRgNetworkExtenderIndex OBJECT-TYPE
    SYNTAX      INTEGER (1..8)
    MAX-ACCESS  not-accessible
    STATUS      current
    DESCRIPTION
        "The index of the the table.  Up to 8 connected devices supported"
    ::= { tchRgNetworkExtenderEntry 1 }

tchRgNetworkExtenderIpAddress OBJECT-TYPE
    SYNTAX      IpAddress
    MAX-ACCESS  read-only
    STATUS      current
    DESCRIPTION
        "The IP Address of the Device"
    ::= { tchRgNetworkExtenderEntry 2 }

tchRgNetworkExtenderDeviceName OBJECT-TYPE
    SYNTAX      OCTET STRING (SIZE(0..32))
    MAX-ACCESS  read-only
    STATUS      current
    DESCRIPTION
        "The Name of the Device as returned by HNAP"
    ::= { tchRgNetworkExtenderEntry 3 }

tchRgNetworkExtenderVenderName OBJECT-TYPE
    SYNTAX      OCTET STRING (SIZE(0..32))
    MAX-ACCESS  read-only
    STATUS      current
    DESCRIPTION
        "The Vender Name as returned by HNAP"
    ::= { tchRgNetworkExtenderEntry 4 }

tchRgNetworkExtenderModelNumber OBJECT-TYPE
    SYNTAX      OCTET STRING (SIZE(0..32))
    MAX-ACCESS  read-only
    STATUS      current
    DESCRIPTION
        "The Model Number of the Device as returned by HNAP"
    ::= { tchRgNetworkExtenderEntry 5 }

tchRgNetworkExtenderFirmwareVersion OBJECT-TYPE
    SYNTAX      OCTET STRING (SIZE(0..32))
    MAX-ACCESS  read-only
    STATUS      current
    DESCRIPTION
        "The Firmware version of the Device as returned by HNAP"
    ::= { tchRgNetworkExtenderEntry 6 }

-- ====================================================
-- Network Extender Radio Status Table
-- ====================================================

tchRgNetworkExtenderRadioTable  OBJECT-TYPE
    SYNTAX      SEQUENCE OF TchRgNetworkExtenderRadioEntry
    MAX-ACCESS  not-accessible
    STATUS      current
    DESCRIPTION
        "Attached Network Extender Radio Table. Maximum of 32 entries (per extender).
        If the attached device has no radios/SSID, this table will be empty"
    ::= { tchRgNetworkExtenders 2 }

tchRgNetworkExtenderRadioEntry OBJECT-TYPE
    SYNTAX      TchRgNetworkExtenderRadioEntry
    MAX-ACCESS  not-accessible
    STATUS      current
    DESCRIPTION
        "A row in the table for Network Extender attached WiFi Radios."
    INDEX       {   tchRgNetworkExtenderIndex,
                                tchRgNetworkExtenderRadioIndex }
    ::= { tchRgNetworkExtenderRadioTable 1 }

TchRgNetworkExtenderRadioEntry ::= SEQUENCE {
        tchRgNetworkExtenderRadioIndex           INTEGER,
        tchRgNetworkExtenderRadioSSID            OCTET STRING,
        tchRgNetworkExtenderRadioBSSID           PhysAddress,
        tchRgNetworkExtenderRadioChannel         OCTET STRING,
        tchRgNetworkExtenderRadioMode            OCTET STRING
    }

tchRgNetworkExtenderRadioIndex OBJECT-TYPE
    SYNTAX      INTEGER (1..32)
    MAX-ACCESS  not-accessible
    STATUS      current
    DESCRIPTION
        "The index of the radio/SSID. Up to 32 SSIDs supported"
    ::= { tchRgNetworkExtenderRadioEntry 1 }

tchRgNetworkExtenderRadioSSID OBJECT-TYPE
    SYNTAX      OCTET STRING (SIZE(0..32))
    MAX-ACCESS  read-only
    STATUS      current
    DESCRIPTION
        "The SSID of the radio as by HNAP"
    ::= { tchRgNetworkExtenderRadioEntry 2 }

tchRgNetworkExtenderRadioBSSID OBJECT-TYPE
    SYNTAX      PhysAddress
    MAX-ACCESS  read-only
    STATUS      current
    DESCRIPTION
        "The BSSID as reported by HNAP"
    ::= { tchRgNetworkExtenderRadioEntry 3 }

tchRgNetworkExtenderRadioChannel OBJECT-TYPE
    SYNTAX      OCTET STRING (SIZE(0..32))
    MAX-ACCESS  read-only
    STATUS      current
    DESCRIPTION
        "Returns the Primary Radio Channel Number as reported by HNAP"
    ::= { tchRgNetworkExtenderRadioEntry 4 }

tchRgNetworkExtenderRadioMode OBJECT-TYPE
    SYNTAX      OCTET STRING (SIZE(0..32))
    MAX-ACCESS  read-only
    STATUS      current
    DESCRIPTION
        "Returns the Radio Operational Mode as reported by HNAP"
    ::= { tchRgNetworkExtenderRadioEntry 5 }

-- ====================================================
-- Network Extender Connected Client Table
-- ====================================================
tchRgNetworkExtenderClientTable  OBJECT-TYPE
    SYNTAX      SEQUENCE OF TchRgNetworkExtenderClientEntry
    MAX-ACCESS  not-accessible
    STATUS      current
    DESCRIPTION
        "Attached Network Extender Client Table. Maximum of 64 Entries per Extender"
    ::= { tchRgNetworkExtenders 3 }

tchRgNetworkExtenderClientEntry OBJECT-TYPE
    SYNTAX      TchRgNetworkExtenderClientEntry
    MAX-ACCESS  not-accessible
    STATUS      current
    DESCRIPTION
        "A row in the table denoting Network Extender Clients."
    INDEX       {   tchRgNetworkExtenderIndex,
                    tchRgNetworkExtenderClientIndex }
    ::= { tchRgNetworkExtenderClientTable  1 }

TchRgNetworkExtenderClientEntry ::= SEQUENCE {
         tchRgNetworkExtenderClientIndex          INTEGER,
         tchRgNetworkExtenderClientMAC            PhysAddress,
         tchRgNetworkExtenderClientInterface      OCTET STRING
    }

tchRgNetworkExtenderClientIndex OBJECT-TYPE
    SYNTAX      INTEGER (1..64)
    MAX-ACCESS  not-accessible
    STATUS      current
    DESCRIPTION
        "The index of the Client."
    ::= { tchRgNetworkExtenderClientEntry 1 }


tchRgNetworkExtenderClientMAC OBJECT-TYPE
    SYNTAX      PhysAddress
    MAX-ACCESS  read-only
    STATUS      current
    DESCRIPTION
        "Returns the client's MAC as reported by HNAP"
    ::= { tchRgNetworkExtenderClientEntry 2 }

tchRgNetworkExtenderClientInterface OBJECT-TYPE
    SYNTAX      OCTET STRING (SIZE(0..32))
    MAX-ACCESS  read-only
    STATUS      current
    DESCRIPTION
        "Returns the client's connected interface per HNAP.   Wifi-2.4, Wifi-5.0, Ethernet, etc"
    ::= { tchRgNetworkExtenderClientEntry 3 }

-- ====================================================
-- Apps Processor MIBs
-- ====================================================

tchRgApps OBJECT IDENTIFIER ::= { tchRg 17 }

tchRgAppsVsaf OBJECT IDENTIFIER ::= { tchRgApps 1 }

tchRgAppsVsafEnable OBJECT-TYPE
    SYNTAX    INTEGER {
                stop(0),
                start(1),
                restart(2)
    }
    MAX-ACCESS  read-write
    STATUS      current
    DESCRIPTION
            "This MIB controls the status of the Videoscape Application Framework running on the Linux processor.
            stop(0) is the default. VSAF is turned off.
            start(1) turns VSAF on.
            restart(2) restarts VSAF (VSAF off then on)."
    DEFVAL { 0 }
    ::= { tchRgAppsVsaf 1 }

tchRgAppsLnx OBJECT IDENTIFIER 
        ::= { tchRgApps 2 }

tchRgAppsLnxUsbEnable OBJECT-TYPE
    SYNTAX      TruthValue
    MAX-ACCESS  read-write
    STATUS      current
    DESCRIPTION
        "Enables or disables the support of USB on the cable gateway. Also it will hide the USB pages in WebUI if it is disabled.
         Once a value is set, it will take effect right away & persists across reboots and all types of resets.
        "  
    DEFVAL { false }
    ::= { tchRgAppsLnx 1 }

tchRgAppsLnxUsbMountTable OBJECT-TYPE
    SYNTAX  SEQUENCE OF TchRgAppsLnxUsbMountEntry
    MAX-ACCESS  not-accessible
    STATUS  current
    DESCRIPTION
            "The list of external device mounted in the system."
    ::= { tchRgAppsLnx 2 }

tchRgAppsLnxUsbMountEntry OBJECT-TYPE
    SYNTAX  TchRgAppsLnxUsbMountEntry
    MAX-ACCESS  not-accessible
    STATUS  current
    DESCRIPTION
            "Details of the externally mounted device via USB"
    INDEX   { tchRgAppsLnxUsbMountTableIndex }
    ::= { tchRgAppsLnxUsbMountTable 1 }

TchRgAppsLnxUsbMountEntry ::= SEQUENCE {
    tchRgAppsLnxUsbMountTableIndex
        Unsigned32,
    tchRgAppsLnxUsbFileSystemName
        OCTET STRING,
    tchRgAppsLnxUsbFileSystemType
        OCTET STRING,
    tchRgAppsLnxUsbTotalSize
        Unsigned32,
    tchRgAppsLnxUsbUsedSize
        Unsigned32,
    tchRgAppsLnxUsbAvailableSize
        Unsigned32,
    tchRgAppsLnxUsbUsedPercentage
        INTEGER,
    tchRgAppsLnxUsbMountedPath
        OCTET STRING
    }

tchRgAppsLnxUsbMountTableIndex OBJECT-TYPE
    SYNTAX  Unsigned32
    MAX-ACCESS  not-accessible
    STATUS  current
    DESCRIPTION
            "Used for indexing the UsbMountTable.
             It has no other purpose."
    ::= { tchRgAppsLnxUsbMountEntry 1 }    

tchRgAppsLnxUsbFileSystemName OBJECT-TYPE
    SYNTAX  OCTET STRING 
    MAX-ACCESS  read-only
    STATUS  current
    DESCRIPTION
            "Name of the mounted filesystem"
    ::= { tchRgAppsLnxUsbMountEntry 2 }

tchRgAppsLnxUsbFileSystemType OBJECT-TYPE
    SYNTAX  OCTET STRING 
    MAX-ACCESS  read-only
    STATUS  current
    DESCRIPTION
            "Type of the mounted filesystem"
    ::= { tchRgAppsLnxUsbMountEntry 3 }

tchRgAppsLnxUsbTotalSize OBJECT-TYPE
    SYNTAX  Unsigned32
    MAX-ACCESS  read-only
    STATUS  current
    DESCRIPTION
            "Displays the total size of the mounted device.
             The unit is in MB."
    ::= { tchRgAppsLnxUsbMountEntry 4 }    

tchRgAppsLnxUsbUsedSize OBJECT-TYPE
    SYNTAX  Unsigned32
    MAX-ACCESS  read-only
    STATUS  current
    DESCRIPTION
            "Displays the used size of the mounted device.
             The unit is in MB."
    ::= { tchRgAppsLnxUsbMountEntry 5 }    

tchRgAppsLnxUsbAvailableSize OBJECT-TYPE
    SYNTAX  Unsigned32
    MAX-ACCESS  read-only
    STATUS  current
    DESCRIPTION
            "Displays the available size of the mounted device.
             The unit is in MB."
    ::= { tchRgAppsLnxUsbMountEntry 6 }    

tchRgAppsLnxUsbUsedPercentage OBJECT-TYPE
    SYNTAX  INTEGER
    MAX-ACCESS  read-only
    STATUS  current
    DESCRIPTION
            "Displays the used percentage of the mounted device."
    ::= { tchRgAppsLnxUsbMountEntry 7 }    

tchRgAppsLnxUsbMountedPath OBJECT-TYPE
    SYNTAX  OCTET STRING 
    MAX-ACCESS  read-only
    STATUS  current
    DESCRIPTION
            "Displays the path where the device is mounted."
    ::= { tchRgAppsLnxUsbMountEntry 8 }

-- ====================================================
-- UHN/GHN MIBs
-- ====================================================

tchRgHN OBJECT IDENTIFIER ::= { tchRg 18 }

tchRgHNEnable OBJECT-TYPE
    SYNTAX  TruthValue
    MAX-ACCESS  read-write
    STATUS  current
    DESCRIPTION
            "Default value is false."
    ::= { tchRgHN    1 }
    
tchRgHNMode OBJECT-TYPE
    SYNTAX  INTEGER {uhnOnly(1), ghn(2)}
    MAX-ACCESS  read-write
    STATUS  current
    DESCRIPTION
            "Set the Home Network mode"
    ::= { tchRgHN    2 }
    
tchRgHNhgwAccessType OBJECT-TYPE
    SYNTAX    INTEGER {
                uHN(1),gHN(2),block(3)
    }
    MAX-ACCESS  read-write
    STATUS      current
    DESCRIPTION
            "This MIB controls the internet access type of HGW device.
            Use UHN(1) as the default gateway for upc device.
            Use GHN(2) as the default gateway for upc device.
            Block(3)."
    DEFVAL { 1 }
    ::= { tchRgHN 3 }    

tchRgHNnonhgwAccessType OBJECT-TYPE
    SYNTAX    INTEGER {
                uHN(1),gHN(2),block(3)
    }
    MAX-ACCESS  read-write
    STATUS      current
    DESCRIPTION
            "This MIB controls the internet access type of non-HGW device.
            Use UHN(1) as the default gateway for non-HGW device.
            Use GHN(2) as the default gateway for non-HGW device.
            Block(3)."
    DEFVAL { 2 }
    ::= { tchRgHN 4 }

tchRgHNIPMMinPoolSize OBJECT-TYPE
    SYNTAX  Unsigned32
    MAX-ACCESS  read-write
    STATUS  current
    DESCRIPTION
            "The minimum IP pool size in IP Manager.
             Default value is 4"  
     DEFVAL { 4 }
    ::= { tchRgHN 5 }
    
tchRgHNIPMInitPoolSize OBJECT-TYPE
    SYNTAX  Unsigned32
    MAX-ACCESS  read-write
    STATUS  current
    DESCRIPTION
            "The initial IP pool size in IP Manager.
             Default value is 20"   
     DEFVAL { 20 }
    ::= { tchRgHN 6 }    

tchRgHNIPMPoolLowWatermark OBJECT-TYPE
    SYNTAX  Unsigned32
    MAX-ACCESS  read-write
    STATUS  current
    DESCRIPTION
            "The low watermark of IP pool size in IP Manager.
             Default value is 4"   
     DEFVAL { 4 }

    ::= { tchRgHN 7 }

tchRgHNIPMPoolLeaseTime OBJECT-TYPE
    SYNTAX  Unsigned32
    MAX-ACCESS  read-write
    STATUS  current
    DESCRIPTION
            "The lease time of IP pool in IP Manager.
             Default value is 180 seconds" 
     DEFVAL { 180 }
    ::= { tchRgHN 8 }    

tchRgHNIPMCurrentLeaseTable OBJECT-TYPE
    SYNTAX  SEQUENCE OF TchRgHNIPMCurrentLeaseEntry
    MAX-ACCESS  not-accessible
    STATUS  current
    DESCRIPTION
            "The list of current IP lease in IP Manager"
    ::= { tchRgHN 9 }

tchRgHNIPMCurrentLeaseEntry OBJECT-TYPE
    SYNTAX  TchRgHNIPMCurrentLeaseEntry
    MAX-ACCESS  not-accessible
    STATUS  current
    DESCRIPTION
            "Details of an IP lease in IP Manager"
    INDEX   { tchRgHNIPMLeaseTableIndex }
    ::= { tchRgHNIPMCurrentLeaseTable 1 }

TchRgHNIPMCurrentLeaseEntry ::= SEQUENCE {
    tchRgHNIPMLeaseTableIndex
        Unsigned32,
    tchRgHNIPMClientIPAddress
        IpAddress,
    tchRgHNIPMClientMACAddress
        MacAddress,
    tchRgHNIPMLeaseState
        INTEGER,
    tchRgHNIPMAcquiredTime
        OCTET STRING,
    tchRgHNIPMExpiredTime
        OCTET STRING,
    tchRgHNIPMClientAcquiredTime
        OCTET STRING,
    tchRgHNIPMClientExpiredTime
        OCTET STRING,
    tchRgHNIPMClientType
        INTEGER
    }

tchRgHNIPMLeaseTableIndex OBJECT-TYPE
    SYNTAX  Unsigned32
    MAX-ACCESS  not-accessible
    STATUS  current
    DESCRIPTION
            "Used for indexing the IPMCurrentLeaseTable.
             It has no other purpose."
    ::= { tchRgHNIPMCurrentLeaseEntry 1 }    

tchRgHNIPMClientIPAddress OBJECT-TYPE
    SYNTAX  IpAddress
    MAX-ACCESS  read-only
    STATUS  current
    DESCRIPTION
            "Client IP address"
    ::= { tchRgHNIPMCurrentLeaseEntry 2 }

tchRgHNIPMClientMACAddress OBJECT-TYPE
    SYNTAX  MacAddress
    MAX-ACCESS  read-only
    STATUS  current
    DESCRIPTION
            "Client MAC address"
    ::= { tchRgHNIPMCurrentLeaseEntry 3 }

tchRgHNIPMLeaseState OBJECT-TYPE
    SYNTAX  INTEGER {available(1), leased(2), expired(3), conflict(4)}
    MAX-ACCESS  read-only
    STATUS  current
    DESCRIPTION
            "IP Lease state"
    ::= { tchRgHNIPMCurrentLeaseEntry 4 }

tchRgHNIPMAcquiredTime OBJECT-TYPE
    SYNTAX  OCTET STRING (SIZE (19))
    MAX-ACCESS  read-only
    STATUS  current
    DESCRIPTION
            "IP acquired time. Format is 'yyyy-mm-dd hh:mm:ss'"
    ::= { tchRgHNIPMCurrentLeaseEntry 5 }

tchRgHNIPMExpiredTime OBJECT-TYPE
    SYNTAX  OCTET STRING (SIZE (19))
    MAX-ACCESS  read-only
    STATUS  current
    DESCRIPTION
            "IP renewal time. Format is 'yyyy-mm-dd hh:mm:ss'"
    ::= { tchRgHNIPMCurrentLeaseEntry 6 }

tchRgHNIPMClientAcquiredTime OBJECT-TYPE
    SYNTAX  OCTET STRING (SIZE (19))
    MAX-ACCESS  read-only
    STATUS  current
    DESCRIPTION
            "Client IP acquired time. Format is 'yyyy-mm-dd hh:mm:ss'"
    ::= { tchRgHNIPMCurrentLeaseEntry 7 }

tchRgHNIPMClientExpiredTime OBJECT-TYPE
    SYNTAX  OCTET STRING (SIZE (19))
    MAX-ACCESS  read-only
    STATUS  current
    DESCRIPTION
            "Client IP renewal time. Format is 'yyyy-mm-dd hh:mm:ss'"
    ::= { tchRgHNIPMCurrentLeaseEntry 8 }

tchRgHNIPMClientType OBJECT-TYPE
    SYNTAX  INTEGER {internalVC(1), externalVC(2), externalHC(3),reserved(4)}
    MAX-ACCESS  read-only
    STATUS  current
    DESCRIPTION
            "DHCP client type"
    ::= { tchRgHNIPMCurrentLeaseEntry 9 }

tchRgHNIPMResetAll OBJECT-TYPE
    SYNTAX  TruthValue
    MAX-ACCESS  read-write
    STATUS  current
    DESCRIPTION
            "If set to true(1), reinitialize entire DHCP pool"
    ::= { tchRgHN 10 }

tchRgHNGHNInitDiscRetries OBJECT-TYPE
    SYNTAX  Unsigned32
    MAX-ACCESS  read-write
    STATUS  current
    DESCRIPTION
            "The number of DHCP discover retries to establish GHN link.
             Default value is 6."
    ::= { tchRgHN 11 }

tchRgHNGHNInitDiscTimeout OBJECT-TYPE
    SYNTAX  Unsigned32
    MAX-ACCESS  read-write
    STATUS  current
    DESCRIPTION
            "Timeout per DHCP discover retry to establish GHN link.
             Default value is 500 miliseconds"
    ::= { tchRgHN 12 }

tchRgHNConnectionType OBJECT-TYPE
    SYNTAX  INTEGER {ethernet(1), wifi(2)}
    MAX-ACCESS  read-write
    STATUS  current
    DESCRIPTION
            "Allow administrator to explicitly specify GHN link interface.
             Default value is ethernet(1)."
    ::= { tchRgHN    13 }

tchRgHNConnectionMode OBJECT-TYPE
    SYNTAX  INTEGER {
        gHNInit(0), uHNInit(1), getPrimaryIP(2), getDummyIP(3), clientConnect(4), clientDisconnect(5), attachLinkDisable(6), unexpectedUHNmode(7), expectedUHNmode(8), waitReInit(9)}
    MAX-ACCESS  read-only
    STATUS  current
    DESCRIPTION
            "Status of the UHN GHN feature machine."
    ::= { tchRgHN    14 }
    
tchRgHNAutoRecovery  OBJECT-TYPE
    SYNTAX  TruthValue  
    MAX-ACCESS  read-write
    STATUS  current
    DESCRIPTION
            "If the flag is true, try to recovery while fail to set up the GHN mode. otherwise, it will work on UHN mode"
    ::= { tchRgHN    15 }
    
tchRgHNGHNPrimaryHomeRouterIPAddress OBJECT-TYPE
    SYNTAX  IpAddress
    MAX-ACCESS  read-only
    STATUS  current
    DESCRIPTION
            "The IP address of external primary home router"
    ::= { tchRgHN  16}
    
tchRgHNGHNPrimaryHomeRouterPrimaryDNS OBJECT-TYPE
    SYNTAX  IpAddress
    MAX-ACCESS  read-only
    STATUS  current
    DESCRIPTION
            "The DNS of external primary home router"
    ::= { tchRgHN  17}
    
tchRgHNGHNPrimaryHomeRouterSecondaryDNS OBJECT-TYPE
    SYNTAX  IpAddress
    MAX-ACCESS  read-only
    STATUS  current
    DESCRIPTION
            "The DNS of external primary home router"
    ::= { tchRgHN  18}

-- ====================================================
-- Ping Mgmt MIBs
-- ====================================================

tchRgPingMgmt OBJECT IDENTIFIER ::= { tchRg 19 }

tchRgPingMgmtTargetAddress OBJECT-TYPE
    SYNTAX      OCTET STRING 
    MAX-ACCESS  read-write
    STATUS      current
    DESCRIPTION
        "Sets the internet address of the entity to be pinged."         
         
    DEFVAL { "" }
    ::= { tchRgPingMgmt 1 }

tchRgPingMgmtInterface OBJECT-TYPE
    SYNTAX INTEGER {
        erouter0(1),
		brlan0(2),
		eCM(3)
    }
    MAX-ACCESS  read-write
    STATUS      current
    DESCRIPTION
        "it sets source interface  to specified  interface name."

    DEFVAL { erouter0 }
    ::= { tchRgPingMgmt 2 }


tchRgPingMgmtNumberOfRepetitions OBJECT-TYPE
    SYNTAX      Unsigned32 
    MAX-ACCESS  read-write
    STATUS      current
    DESCRIPTION
         "Allows the client to set the number of pings to be sent.
          This can be set to any number between 1 and (2^32 - 1)"  

    DEFVAL { 3 }
    ::= { tchRgPingMgmt 3 }

tchRgPingMgmtTimeout OBJECT-TYPE
    SYNTAX      Unsigned32 
    MAX-ACCESS  read-write
    STATUS      current
    DESCRIPTION
        "Allows the client to set the amount of time (in milliseconds) that the
         device should wait for a reply after sending a ping."

    DEFVAL { 1000 }
    ::= { tchRgPingMgmt 4 }

tchRgPingMgmtDataBlockSize OBJECT-TYPE
    SYNTAX      Unsigned32
    MAX-ACCESS  read-write
    STATUS      current
    DESCRIPTION
        " Specifies the number of data bytes to be sent.  The default is 56, which translates into  64  ICMP  data
          bytes when combined with the 8 bytes of ICMP header data."

    DEFVAL { 56 }
    ::= { tchRgPingMgmt 5 }

tchRgPingMgmtPingNow OBJECT-TYPE
    SYNTAX INTEGER {                        
        none(1),
        requested(2),
        complete(3),
        errorCannotResolveHostName(4),
        errorInternal(5),
        errorOther(6),
        requestAborted(11),
        requestStop(13)                                            
    }
    MAX-ACCESS  read-write
    STATUS      current
    DESCRIPTION
         "Starts or stops the pings. This mib allows to set only value, 2(Requested), Rest of the values are readable. only"

    DEFVAL { 1 }
        ::= { tchRgPingMgmt 6 }

tchRgPingMgmtSuccessCount OBJECT-TYPE
    SYNTAX      Unsigned32 
    MAX-ACCESS  read-only
    STATUS      current
    DESCRIPTION
        " Indicates the number of replies received since the ping was started."
         
    DEFVAL { 0 }
    ::= { tchRgPingMgmt 7 }

tchRgPingMgmtFailureCount OBJECT-TYPE
    SYNTAX      Unsigned32 
    MAX-ACCESS  read-only
    STATUS      current
    DESCRIPTION
        " Indicates the number of packets sent minus packets received since the ping was started."      
        
    DEFVAL { 0 }
    ::= { tchRgPingMgmt 8 }

tchRgPingMgmtAverageResponseTime OBJECT-TYPE
    SYNTAX      Unsigned32 
    MAX-ACCESS  read-only
    STATUS      current
    DESCRIPTION
         "It specifies the time taken for a packet to reach the destination and come back. 
          or measure of Round Trip Time or response time and is displayed in milliseconds."
 
    DEFVAL { 0 }
    ::= { tchRgPingMgmt 9 }

tchRgPingMgmtMinimumResponseTime OBJECT-TYPE
    SYNTAX      Unsigned32 
    MAX-ACCESS  read-only
    STATUS      current
    DESCRIPTION
        "It specifies the Minimum time taken for a packet to reach the destination and come back."
    
    DEFVAL { 0 }
    ::= { tchRgPingMgmt 10 }

tchRgPingMgmtMaximumResponseTime OBJECT-TYPE
    SYNTAX      Unsigned32 
    MAX-ACCESS  read-only 
    STATUS      current
    DESCRIPTION
        " It specifies the Maximum time taken for a packet to reach the destination and come back."

    DEFVAL { 0 }
    ::= { tchRgPingMgmt 11 }

-- ====================================================
-- DNS MIBs
-- ====================================================
tchRgDNS OBJECT IDENTIFIER ::=  { tchRg 20 }

tchRgDNSProxyEnable OBJECT-TYPE
    SYNTAX      TruthValue
    MAX-ACCESS  read-write
    STATUS      current
	DESCRIPTION
	    "Enables/Disables the DNS Proxy.
		If true(1), DNS proxy is Enabled -> clients connected will get the gateway IP as DNS server.
		If false(2), DNS proxy is Disabled -> clients connected will get the external DNS server."
	DEFVAL { false }
    ::= { tchRgDNS 1 }		
	
tchRgDNSLanGuiURL OBJECT-TYPE
    SYNTAX      SnmpAdminString
    MAX-ACCESS  read-write
    STATUS      current
	DESCRIPTION
	    "This MIB gives the name of url, to access Lan side webui page. We can access webui from lan clients 
		from this name, instead of actual gateway lan ip."	
    ::= { tchRgDNS 2 }

tchRgDNSTable OBJECT-TYPE
        SYNTAX SEQUENCE OF TchRgDNSEntry
        MAX-ACCESS not-accessible
        STATUS current
        DESCRIPTION
                "Table of DNS proxy "
        ::= { tchRgDNS 3 }

tchRgDNSEntry OBJECT-TYPE
    SYNTAX      TchRgDNSEntry
    MAX-ACCESS  not-accessible
    STATUS      current
    DESCRIPTION
            "Table of DNS proxy "
    INDEX { tchRgDNSEnable }
    ::= { tchRgDNSTable 1 }

TchRgDNSEntry ::= SEQUENCE {
    tchRgDNSEnable       TruthValue,
    tchRgDNSUsername     OCTET STRING,
    tchRgDNSPassword     OCTET STRING,
    tchRgDNSDomain       OCTET STRING,
	tchRgDNSServiceName  OCTET STRING 
    }

tchRgDNSEnable OBJECT-TYPE
    SYNTAX      TruthValue
    MAX-ACCESS  read-write
    STATUS      current
    DESCRIPTION
            "The index"
    ::= { tchRgDNSEntry 1 }

tchRgDNSUsername OBJECT-TYPE
    SYNTAX      OCTET STRING
    MAX-ACCESS  read-write
    STATUS      current
    DESCRIPTION
            "User Name for using the DNS service."
    ::= { tchRgDNSEntry 2 }

tchRgDNSPassword OBJECT-TYPE
    SYNTAX      OCTET STRING
    MAX-ACCESS  read-write
    STATUS      current
    DESCRIPTION
            "Password for using the DNS service."
    ::= { tchRgDNSEntry 3 }

tchRgDNSDomain OBJECT-TYPE
    SYNTAX      OCTET STRING
    MAX-ACCESS  read-write
    STATUS      current
    DESCRIPTION
            "Domain name, where service belongs."
    ::= { tchRgDNSEntry 4 }

tchRgDNSServiceName OBJECT-TYPE
    SYNTAX      OCTET STRING
    MAX-ACCESS  read-write
    STATUS      current
    DESCRIPTION
            "Name of the DNS service"
    ::= { tchRgDNSEntry 5 }	

tchRgDNSRedirectEnable OBJECT-TYPE
    SYNTAX      TruthValue
    MAX-ACCESS  read-write
    STATUS      current
    DESCRIPTION
	    "Enable/Disable redirection to a help page when Internet is down"
    DEFVAL { false }
    ::= { tchRgDNS 4 }


--- ============ Edns0 Section ============

tchRgEdns0   OBJECT IDENTIFIER ::=  { tchRgDNS 5 }

tchRgEdns0Enable OBJECT-TYPE
    SYNTAX      TruthValue
    MAX-ACCESS  read-write
    STATUS      current
    DESCRIPTION      
        "MIB to control the eDNS0 activation state. Default behavior is disabled (0).
        If set to true(1), eDNS0 feature is enabled.
        NOTE: VFG will continue to use tchRgIpMgmtEdns0Enable.  All other products will use tchRgEdns0Enable"
    ::= { tchRgEdns0 1 }

tchRgEdns0Mode OBJECT-TYPE
    SYNTAX INTEGER {
            addClntMac(1), 
            addClntAndGwMac(2)
     }
    MAX-ACCESS      read-write
    STATUS          current
    DESCRIPTION
        "Determine Which MACs to add to EDNS0 section.
         For option one, addClntMac, we add the LAN client's MAC that is doing DNS query.
         For option two, addClntAndGwMac, we add the LAN client's MAC and the Gateway MAC.
         Default is addClntMac"
    ::= { tchRgEdns0 2 }

tchRgEdns0ApplySettings OBJECT-TYPE
    SYNTAX      TruthValue
    MAX-ACCESS  read-write
    STATUS      current
    DESCRIPTION      
        "Triggers mibs above to be applied"
    ::= { tchRgEdns0 3 }

tchRgEdns0Format OBJECT-TYPE
    SYNTAX INTEGER {
            textBasedMac(1), 
            base64Mac(2)
     }
    MAX-ACCESS      read-write
    STATUS          current
    DESCRIPTION
        "Determine which format to use for MAC encoding.
         Option 1, textBasedMac, enables MAC format as text. This is the default.
         Option 2, base64Mac, encodes the MAC using base64."

    DEFVAL { 1 }
    ::= { tchRgEdns0 4 }

-- ====================================================
-- TCH RG Memory  MIBs
-- ====================================================
tchRgStats OBJECT IDENTIFIER ::=  { tchRg 21 }

tchRgStatsMemoryTotal OBJECT-TYPE
    SYNTAX      DisplayString
    MAX-ACCESS  read-only
    STATUS      current
    DESCRIPTION
            "Displays the available  amount of RAM installed on the gateway"
    ::= { tchRgStats 1 }     
     
tchRgStatsMemoryUsed OBJECT-TYPE
    SYNTAX      DisplayString
    MAX-ACCESS  read-only
    STATUS      current
    DESCRIPTION
            "Displays the amount of RAM being used, currently allocated, by various gateway processes"  
    ::= { tchRgStats 2 }

tchRgStatsMemoryFree OBJECT-TYPE
    SYNTAX      DisplayString
    MAX-ACCESS  read-only
    STATUS      current
    DESCRIPTION
            "Displays the amount of free RAM, RAM that can allocated by various processes, on the gateway"
        ::= { tchRgStats 3 }

tchRgStatsCpuUtilization OBJECT-TYPE
    SYNTAX          Integer32
    MAX-ACCESS      read-only
    STATUS          current
    DESCRIPTION 
             "RG CPU utilization"
        ::= { tchRgStats 4 }


tchRgEvent        OBJECT IDENTIFIER ::= { tchRg 22 }     --tcgRgMIBobjects

--=========== FIRST INDEX SELECTING WHICH LOG =======================

-- Index to specify which log is addressed: eRouter, or one per SSID
tchRgEventLogTypeIndex OBJECT-TYPE
    SYNTAX INTEGER {
            eRouter(1), 
            wifi(2)
     }
    MAX-ACCESS      read-only
    STATUS          current
    DESCRIPTION
        "The index of tchRgLogs per type"
    ::= { tchRgEvent 1 }

-- Event table

tchRgEventTable OBJECT-TYPE
        SYNTAX      SEQUENCE OF TchRgEventEntry
        MAX-ACCESS  not-accessible
        STATUS      current
        DESCRIPTION
            "Contains a log of network and device events that may be
             of interest in fault isolation and troubleshooting.
             If the local(0) bit is set in tchRgEvReporting,
             entries in this table MUST persist across reboots."
        ::= {  tchRgEvent 2 }

tchRgEventEntry OBJECT-TYPE
        SYNTAX      TchRgEventEntry
        MAX-ACCESS  not-accessible
        STATUS      current
        DESCRIPTION
            "Describes a network or device event that may be of
             interest in fault isolation and troubleshooting.
             Multiple sequential identical events are represented by
             incrementing tchRgEvCounts and setting
             tchRgEvLastTime to the current time rather than
             creating multiple rows.

             Entries are created with the first occurrence of an
             event.  tchRgEvClearTable can be used to clear the
             table.  Individual events cannot be deleted."
        INDEX { tchRgEventLogTypeIndex, tchRgEvIndex }
        ::= { tchRgEventTable 1 }

TchRgEventEntry ::= SEQUENCE {
            tchRgEvIndex           Integer32,
            tchRgEvFirstTime       DateAndTime,
            tchRgEvLastTime        DateAndTime,
            tchRgEvCounts          Counter32,
            tchRgEvLevel           INTEGER,
            tchRgEvId              Unsigned32,
            tchRgEvText            SnmpAdminString
        }

tchRgEvIndex OBJECT-TYPE
        SYNTAX      Integer32 (1..2147483647)
        MAX-ACCESS  not-accessible
        STATUS      current
        DESCRIPTION
            "Provides relative ordering of the objects in the event
             log.  This object will always increase except when
             (a) the log is reset via tchRgEvControl,
             (b) the device reboots and does not implement
             non-volatile storage for this log, or (c) it reaches
             the value 2^31.  The next entry for all the above
             cases is 1."
        ::= { tchRgEventEntry 1 }

tchRgEvFirstTime OBJECT-TYPE
        SYNTAX      DateAndTime
        MAX-ACCESS  read-only
        STATUS      current
        DESCRIPTION
            "The value of tchRgDateTime at the time this entry was
             created."
        ::= { tchRgEventEntry 2 }

tchRgEvLastTime OBJECT-TYPE
        SYNTAX      DateAndTime
        MAX-ACCESS  read-only
        STATUS      current
        DESCRIPTION
            "When an entry reports only one event, this object will
             have the same value as the corresponding instance of
             tchRgEvFirstTime.  When an entry reports multiple
             events, this object will record the value that
             tchRgDateTime had when the most recent event for this
             entry occurred."
        ::= { tchRgEventEntry 3 }

-- This object was renamed from tchRgEvCount to meet naming
-- requirements for Counter32
tchRgEvCounts OBJECT-TYPE
        SYNTAX      Counter32
        UNITS       "events"
        MAX-ACCESS  read-only
        STATUS      current
        DESCRIPTION
            "The number of consecutive event instances reported by
             this entry.  This starts at 1 with the creation of this
             row and increments by 1 for each subsequent duplicate
             event."
        ::= { tchRgEventEntry 4 }
tchRgEvLevel OBJECT-TYPE
        SYNTAX INTEGER {
            emergency(1),
            alert(2),
            critical(3),
            error(4),
            warning(5),
            notice(6),
            information(7),
            debug(8)
        }
        MAX-ACCESS  read-only
        STATUS      current
        DESCRIPTION
             " TCH:For simplification here we considered only 3 
             priorities: alert(2), critical(3), and notice(6).

	     The priority level of this event, as defined by the
             vendor.  These are ordered from most serious (emergency)
             to least serious (debug).

             emergency(1) events indicate vendor-specific fatal
             hardware or software errors that prevent normal system
             operation.

             alert(2) events indicate a serious failure that causes
             the reporting system to reboot but that is not caused by
             hardware or software malfunctioning.

             critical(3) events indicate a serious failure that
             requires attention and prevents the device from
             transmitting data but that could be recovered without
             rebooting the system.

             error(4) and warning(5) events indicate that a failure
             occurred that could interrupt the normal data flow but
             that does not cause the device to re-register.

             notice(6) and information(7) events indicate a
             milestone or checkpoint in normal operation that could
             be of particular importance for troubleshooting.

             debug(8) events are reserved for vendor-specific

             events.

             During normal operation, no event more
             critical than notice(6) should be generated.  Events
             between warning and emergency should be generated at
             appropriate levels of problems (e.g., emergency when the
             box is about to crash)."
        ::= { tchRgEventEntry 5 }

--
-- It is strongly recommended that implementors follow the CableLabs
-- enumerations for tchRgEvId, per the DOCSIS OSSIv1.1 spec
-- and follow-on specifications.
--

tchRgEvId OBJECT-TYPE
        SYNTAX      Unsigned32
        MAX-ACCESS  read-only
        STATUS      current
        DESCRIPTION
            "For this product, uniquely identifies the type of event
             that is reported by this entry."
        REFERENCE
            "DOCSIS OSSI 1.1 Specification, Appendix H and
             DOCSIS OSSI 2.0 Specification, Annex D."
        ::= { tchRgEventEntry 6 }

tchRgEvText OBJECT-TYPE
        SYNTAX      SnmpAdminString
        MAX-ACCESS  read-only
        STATUS      current
        DESCRIPTION
            "Provides a human-readable description of the event,
             including all relevant context (interface numbers,
             etc.)."
        ::= { tchRgEventEntry 7 }


--================= LOG RESET PER TYPE ============================

tchRgEvClearTable OBJECT-TYPE
        SYNTAX SEQUENCE OF TchRgEvClearEntry
        MAX-ACCESS  not-accessible
        STATUS      current
        DESCRIPTION
            "One table to cover each type of log individually."
        ::= { tchRgEvent 3 }

tchRgEvClearEntry OBJECT-TYPE
    SYNTAX TchRgEvClearEntry
        MAX-ACCESS  not-accessible
        STATUS      current
        DESCRIPTION
        ""
        INDEX { tchRgEventLogTypeIndex }   -- Specified at the beginning of the group
                ::= { tchRgEvClearTable 1 }

TchRgEvClearEntry ::= SEQUENCE {    
        
        tchRgEvClearLogs    INTEGER
}
  
tchRgEvClearLogs OBJECT-TYPE
        SYNTAX INTEGER {
            resetLog(1),    --Setting this object to resetLog(1) empties the event log.  All data is deleted.
            noAction(2)
                    }
        MAX-ACCESS  read-write
        STATUS      current
        DESCRIPTION
            "Clears the log "
        ::= { tchRgEvClearEntry 1 }


------------------------------------------------------------

--
-- The following table controls the reporting of the various classes
-- of events.
--

tchRgEvControlTable OBJECT-TYPE
        SYNTAX      SEQUENCE OF TchRgEvControlEntry
        MAX-ACCESS  not-accessible
        STATUS      current
        DESCRIPTION
            "This table allows control of the reporting of event
             classes.  For each event priority, a combination of

             logging and reporting mechanisms may be chosen.  The
             mapping of event types to priorities is
             vendor dependent.  Vendors may also choose to allow
             the user to control that mapping through proprietary
             means.  Table entries MUST persist across reboots for
             CMTS devices and MUST NOT persist across reboots for CM
             devices."
        ::= {  tchRgEvent 4 }

tchRgEvControlEntry OBJECT-TYPE
        SYNTAX      TchRgEvControlEntry
        MAX-ACCESS  not-accessible
        STATUS      current
        DESCRIPTION
            "Allows configuration of the reporting mechanisms for a
             particular event priority."
        INDEX { tchRgEventLogTypeIndex, tchRgEvCtrlPriority }
        ::= { tchRgEvControlTable 1 }

TchRgEvControlEntry ::= SEQUENCE {
            tchRgEvCtrlPriority       INTEGER,
            tchRgEvCtrlReporting       BITS
        }

tchRgEvCtrlPriority OBJECT-TYPE
        SYNTAX INTEGER {
            alert(2),
            critical(3),
            notice(6)
        }
        MAX-ACCESS  not-accessible
        STATUS      current
        DESCRIPTION
            "
             TCH:For simplification here we considered only 3 priorities.

             The priority level that is controlled by this
             entry.  These are ordered from most (emergency) to least
             (debug) critical.  Each event with a CM or CMTS has a
             particular priority level associated with it (as defined
             by the vendor).

             alert(2) events indicate a serious failure that causes
             the reporting system to reboot but is not caused by
             hardware or software malfunctioning.

             critical(3) events indicate a serious failure that
             requires attention and prevents the device from
             transmitting data but that could be recovered without
             rebooting the system.

             notice(6) events indicate a
             milestone or checkpoint in normal operation that could
             be of particular importance for troubleshooting.

             During normal operation, no event more
             critical than notice(6) should be generated.  Events
             between warning and emergency should be generated at
             appropriate levels of problems (e.g., emergency when the
             box is about to crash)."
        ::= { tchRgEvControlEntry 1 }

tchRgEvCtrlReporting OBJECT-TYPE
        SYNTAX BITS {
            local(0),
            syslog(1)
         }
        MAX-ACCESS  read-write
        STATUS      current
        DESCRIPTION
            "
             TCH: Let's keep this field to control the enabling of the logs
              by setting bit 0. Other options are not considered yet, bit 1 will 
              be used later. Note that it must be set for each priority.

             Defines the action to be taken on occurrence of this
             event class.  Implementations may not necessarily
             support all options for all event classes but at
             minimum must allow traps and syslogging to be
             disabled.

             If the local(0) bit is set, then log to the internal
             log and update non-volatile store, for backward
             compatibility with the original RFC 2669 definition.
             If the traps(1) bit is set, then generate
             an SNMP trap; if the syslog(2) bit is set, then
             send a syslog message (assuming that the syslog address
             is set).  If the localVolatile(8) bit is set, then
             log to the internal log without updating non-volatile
             store.  If the stdInterface(9) bit is set, then the
             agent ignores all other bits except the local(0),
             syslog(2), and localVolatile(8) bits.  Setting the
             stdInterface(9) bit indicates that RFC3413 and
             RFC3014 are being used to control event reporting
             mechanisms."
        ::= { tchRgEvControlEntry 2 }    
        
-- ====================================================
-- TCH RG Speed Test  MIBs
-- ====================================================

tchRgSpeedTest        OBJECT IDENTIFIER ::= { tchRg 23 }     --tcgRgMIBobjects

tchRgIperfSpeedTest OBJECT IDENTIFIER ::= { tchRgSpeedTest 1 }

tchRgIperfServerAddrType OBJECT-TYPE
    SYNTAX  InetAddressType{
        unknown(0),
        ipv4(1),
        ipv6(2)
    }
    MAX-ACCESS read-write
    STATUS current
    DESCRIPTION
        "Whether the Iperf Server is ipv4 or ipv6.
         IPv6 is not supported currently."
    DEFVAL { ipv4 }
    ::= { tchRgIperfSpeedTest 1 }

tchRgIperfServerAddr OBJECT-TYPE
    SYNTAX      InetAddress
    MAX-ACCESS  read-write
    STATUS      current
    DESCRIPTION
            "IP Address, v4 or v6, of Iperf Server on the WAN.
             IPv6 is not supported currently."

    ::= { tchRgIperfSpeedTest 2 }

tchRgIperfProtocol OBJECT-TYPE
    SYNTAX  INTEGER {
        udp(1),
        tcp(2)
        }
    MAX-ACCESS  read-write
    STATUS      current
    DESCRIPTION
            "IP protocol to use during Iperf test.
             Default value is TCP."
    DEFVAL { 2 }
    ::= { tchRgIperfSpeedTest 3 }

tchRgIperfMode OBJECT-TYPE
    SYNTAX  INTEGER {
        ipv4(1),
        ipv6(2)
        }
    MAX-ACCESS  read-write
    STATUS      current
    DESCRIPTION
            "Whether the Iperf Test will be conducted in ipv4 or ipv6.
             IPv6 not supported currently"
    DEFVAL { 1 }
    ::= { tchRgIperfSpeedTest 4 }

tchRgIperfPort OBJECT-TYPE
    SYNTAX      INTEGER
    MAX-ACCESS  read-write
    STATUS      current
    DESCRIPTION
        "The UDP/TCP port to be used for the Iperf Test."
    DEFVAL { 5001 }
    ::= { tchRgIperfSpeedTest 5 }

tchRgIperfTestTime OBJECT-TYPE
    SYNTAX  INTEGER
    MAX-ACCESS  read-write
    STATUS      current
    DESCRIPTION
            "Duration of Iperf Test, in secs"
    DEFVAL { 30 }
    ::= { tchRgIperfSpeedTest 6 }

tchRgIperfBandwidth OBJECT-TYPE
    SYNTAX  INTEGER {
        kiloBitsPerSec(1),
        megaBitsPerSec(2),
        gigaBitsPerSec(3)
        }
    MAX-ACCESS  read-write
    STATUS      current
    DESCRIPTION
            "The format of the iperf test results.  The options are KBits/sec, Mbits/sec, or GBits/sec.
             Only megaBitsPerSec is currently supported."
    DEFVAL { 2 }
    ::= { tchRgIperfSpeedTest 7 }

tchRgIperfWindowSize OBJECT-TYPE
    SYNTAX  INTEGER 
    MAX-ACCESS  read-write
    STATUS      current
    DESCRIPTION
            "The value window size, is only valid if the test protocol is TCP. The maximum value of a TCP window size is 65KB. 
             The default for this iperf test is 64KB.  WindowSize should be updated in 1kB increments (1000)."
    DEFVAL { 64000 }
    ::= { tchRgIperfSpeedTest 8 }

tchRgIperfMSS OBJECT-TYPE
    SYNTAX  INTEGER 
    MAX-ACCESS  read-write
    STATUS      current
    DESCRIPTION
            "The value mss, or maximum segment size, is only valid if the test protocol is TCP. MSS is usually MTU-40bytes. Therefore the default value is 1460, 1500(MTU size) - 40. 
             The default for this iperf test is 64KB"
    DEFVAL { 1460 }
    ::= { tchRgIperfSpeedTest 9 }

tchRgIperfParallelStreams OBJECT-TYPE
    SYNTAX  INTEGER 
    MAX-ACCESS  read-write
    STATUS      current
    DESCRIPTION
            "Parallel Streams defines the number of iperf test to be run at the same time.  The default value is 1.  Parallel Streams is only valid for TCP"
    DEFVAL { 1 }
    ::= { tchRgIperfSpeedTest 10 }

tchRgIperfTestStatus OBJECT-TYPE
    SYNTAX  INTEGER {
        none(0),
        requested(1),
        requestedUpstream(2),
        requestedDownstream(3),
        complete(4),
        cancel(5),
        error(6)
        }
    MAX-ACCESS  read-write
    STATUS      current
    DESCRIPTION
            "Iperf Test Status. Requested, RequestedUpstreami, RequestedDownStream, and Cancel are the only writable values.
             None means no test is running.
             Requested means Upstream and Downstream test is running.
             RequestedUpstream means only upstream test is running.
             RequestedDownstream means only downstream test is running.
             Complete means all test have been executed. 
             Cancel means to cancel any executing test.
             Error means there was a problem executing the test. "
    ::= { tchRgIperfSpeedTest 11 }

tchRgIperfDownstreamTestResults OBJECT-TYPE
    SYNTAX      DisplayString
    MAX-ACCESS  read-only
    STATUS      current
    DESCRIPTION
        "Downstream Results as specified when setting tchRgIperfBandwidth. 
         Not valid when Requested Test is Upstream only"
    ::= { tchRgIperfSpeedTest 12 }

tchRgIperfUpstreamTestResults OBJECT-TYPE
    SYNTAX      DisplayString
    MAX-ACCESS  read-only
    STATUS      current
    DESCRIPTION
        "Upstream Results as specified when setting tchRgIperfBandwidth.
         Not valid when Requested Test is Downstream only"
    ::= { tchRgIperfSpeedTest 13 }

tchRgIperfEnableWebuiPage OBJECT-TYPE
    SYNTAX TruthValue
    MAX-ACCESS read-write
    STATUS current
    DESCRIPTION
        "Sets webui bitmask to enable Iperf Speed Test Page in GUI."
    ::= { tchRgIperfSpeedTest 14 }

-- ====================================================
-- Traceroute Mgmt MIBs
-- ====================================================
 
tchRgTracertMgmt OBJECT IDENTIFIER ::= { tchRg 24 }

tchRgTracertMgmtTargetAddress OBJECT-TYPE
    SYNTAX  InetAddress
    MAX-ACCESS  read-write
    STATUS  current
    DESCRIPTION
            "Sets the internet address of the entity to be traceroute."
    ::= { tchRgTracertMgmt 1 }

tchRgTracertMgmtInterface OBJECT-TYPE
    SYNTAX INTEGER {
        eRoute(1),
        lan0(2),
        eCM(3)
        }
    MAX-ACCESS  read-write
    STATUS      current
    DESCRIPTION
        "It sets source interface to specified interface name."
    DEFVAL { 1 }
    ::= { tchRgTracertMgmt 2 }

tchRgTracertMgmtMaxHopNum OBJECT-TYPE
    SYNTAX INTEGER (1..32)
    MAX-ACCESS read-write
    STATUS current
    DESCRIPTION
        ""
    DEFVAL { 30 }
    ::= { tchRgTracertMgmt 3 }

tchRgTracertMgmtDataSize OBJECT-TYPE
    SYNTAX INTEGER (0..1500)
    UNITS       "bytes"
    MAX-ACCESS     read-write
    STATUS         current
    DESCRIPTION
        ""
    DEFVAL { 0 }
    ::= { tchRgTracertMgmt 4 }

tchRgTracertMgmtUdpPort OBJECT-TYPE
    SYNTAX      InetPortNumber
    MAX-ACCESS  read-write
    STATUS      current
    DESCRIPTION
            ""
    DEFVAL { 33434 }
    ::= { tchRgTracertMgmt 5 }

tchRgTracertMgmtNumOfTries OBJECT-TYPE
    SYNTAX     INTEGER  (1..10)
    MAX-ACCESS read-write
    STATUS     current
    DESCRIPTION
        ""
    DEFVAL { 3 }
    ::= { tchRgTracertMgmt 6 }

tchRgTracertMgmtTimeout OBJECT-TYPE
    SYNTAX INTEGER (1..65535)
    UNITS "seconds"
    MAX-ACCESS read-write
    STATUS current
    DESCRIPTION
        ""
    DEFVAL { 3 }
    ::= { tchRgTracertMgmt 7 }

tchRgTracertMgmtMaxHopsCount OBJECT-TYPE
    SYNTAX          OCTET STRING (SIZE(0..32))
    MAX-ACCESS      read-only
    STATUS          current
    DESCRIPTION
        ""
    ::= { tchRgTracertMgmt 8 }

tchRgTracertMgmtState OBJECT-TYPE
    SYNTAX INTEGER {
        request(1),
        complete(2)
        }
    MAX-ACCESS  read-write
    STATUS      current
    DESCRIPTION
        ""
    DEFVAL {2}
    ::= { tchRgTracertMgmt 9 }

tchRgTracertMgmtResultTable OBJECT-TYPE
    SYNTAX  SEQUENCE OF TchRgTracertMgmtResultEntry
    MAX-ACCESS  not-accessible
    STATUS  current
    DESCRIPTION
            ""
    ::= { tchRgTracertMgmt 10 }

tchRgTracertMgmtResultEntry OBJECT-TYPE
    SYNTAX      TchRgTracertMgmtResultEntry
    MAX-ACCESS  not-accessible
    STATUS      current
    DESCRIPTION
            ""
    INDEX { tchRgTracertMgmtResultIndex }
    ::= { tchRgTracertMgmtResultTable 1 }

TchRgTracertMgmtResultEntry ::= SEQUENCE {
    tchRgTracertMgmtResultIndex      Unsigned32,
    tchRgTracertMgmtResultStation    OCTET STRING,
    tchRgTracertMgmtResultRTTimes    OCTET STRING
    }

tchRgTracertMgmtResultIndex OBJECT-TYPE
    SYNTAX  Unsigned32
    MAX-ACCESS  not-accessible
    STATUS  current
    DESCRIPTION
            ""
    ::= { tchRgTracertMgmtResultEntry 1 }

tchRgTracertMgmtResultStation OBJECT-TYPE
    SYNTAX  OCTET STRING (SIZE (0..256))
    MAX-ACCESS  read-only
    STATUS  current
    DESCRIPTION
            ""
    ::= { tchRgTracertMgmtResultEntry 2 }

tchRgTracertMgmtResultRTTimes OBJECT-TYPE
    SYNTAX  OCTET STRING (SIZE (0..256))
    MAX-ACCESS  read-only
    STATUS  current
    DESCRIPTION
            ""
    ::= { tchRgTracertMgmtResultEntry 3 }

tchRgTracertMgmtTargetAddressType OBJECT-TYPE
    SYNTAX  InetAddressType{
        unknown(0),
        ipv4(1),
        ipv6(2)
    }
    MAX-ACCESS read-write
    STATUS current
    DESCRIPTION
        "Whether the Tracert Target Address is ipv4 or ipv6"
    DEFVAL { ipv4 }
    ::= { tchRgTracertMgmt 11 }

-- ====================================================
-- 3G/4G Backup MIBs
-- ====================================================

tchRg3g4g OBJECT IDENTIFIER ::= { tchRg 25 }

tchRg3g4gEnable OBJECT-TYPE
    SYNTAX TruthValue
    MAX-ACCESS read-write
    STATUS current
    DESCRIPTION "Enable/Disable of 3g/4g backup functionality"
    DEFVAL { false }
    ::= { tchRg3g4g 1 }

tchRg3g4gMode OBJECT-TYPE
    SYNTAX INTEGER { 
        disable(0),
        manual(1),
        auto(2) }
    MAX-ACCESS    read-write
    STATUS        current
    DESCRIPTION "Mode setting of 3g/4g functionality. When set to manual, switch to 3g/4g immediately.
                 When set to auto, switching to 3g/4g is determined by the WAN connectivity."
    DEFVAL {0}
    ::= { tchRg3g4g 2 }

tchRg3g4gTtl OBJECT-TYPE
    SYNTAX     INTEGER 
    MAX-ACCESS read-write
    STATUS     current
    DESCRIPTION
        "Interval in seconds to ping dns ip, resolve dns name. If ping fails then gateway
         may switch to 3g/4g backup. Switching to 3g/4g will determined by 3g/4g enable mib."
    DEFVAL { 120 }
    ::= { tchRg3g4g 3 }

-- ====================================================
-- RG Access Control ListMIBs
-- ====================================================

tchRgAcl OBJECT IDENTIFIER ::= { tchRg 26 }

tchRgAclWebui OBJECT-TYPE
       SYNTAX      SEQUENCE OF TchRgAclWebuiEntry
       MAX-ACCESS  not-accessible
       STATUS      current
       DESCRIPTION
               "Used to give explicit access to Gateway's webui. 
                Clients connected to guest networks can get access to webui vi tchRgAclWebui."

    ::= { tchRgAcl 1 }

tchRgAclWebuiEntry OBJECT-TYPE
    SYNTAX      TchRgAclWebuiEntry
    MAX-ACCESS  not-accessible
    STATUS      current
    DESCRIPTION
            ""
    INDEX { tchRgAclWebuiIndex }
    ::= { tchRgAclWebui 1 }

TchRgAclWebuiEntry ::= SEQUENCE {
    tchRgAclWebuiIndex         INTEGER,
    tchRgAclWebuiMacAddress    MacAddress,
    tchRgAclWebuiAccessEnable  TruthValue
    }

tchRgAclWebuiIndex OBJECT-TYPE
    SYNTAX  INTEGER
    MAX-ACCESS  not-accessible
    STATUS  current
    DESCRIPTION
            ""
    ::= { tchRgAclWebuiEntry 1 }

tchRgAclWebuiMacAddress OBJECT-TYPE
    SYNTAX  MacAddress
    MAX-ACCESS  read-write
    STATUS  current
    DESCRIPTION
            "Client MAC address"
    ::= { tchRgAclWebuiEntry 2 }

tchRgAclWebuiAccessEnable OBJECT-TYPE
    SYNTAX TruthValue
    MAX-ACCESS read-write
    STATUS current
    DESCRIPTION "False explicitly blocks access to webui, even for Primary LAN clients.
                 True enables access to webui, even for guest LAN clients."
    DEFVAL { false }
    ::= { tchRgAclWebuiEntry 3 }

END
