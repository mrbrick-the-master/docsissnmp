--****************************************************************************
--                                                                          
-- Copyright (c) 2003-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-parentalcontrol-mgmt.mib
--    Author:   Kevin O'Neal
--    Creation Date: 4-april-2003
--
--****************************************************************************
--    Description:
--
--              private MIB for runtime (not factory) parental control
--
--****************************************************************************
--    Revision History:
--
--****************************************************************************

BRCM-PARENTALCONTROL-MGMT-MIB DEFINITIONS ::= BEGIN

IMPORTS
    MODULE-IDENTITY,
    OBJECT-TYPE
        FROM SNMPv2-SMI
    TruthValue,
    DisplayString,
    DateAndTime
        FROM SNMPv2-TC 
    cableDataMgmtMIBObjects
        FROM BRCM-CABLEDATA-MGMT-MIB;
                
parentalControlMgmt MODULE-IDENTITY
    LAST-UPDATED "201407290000Z"
    ORGANIZATION "Broadcom Corporation"
    CONTACT-INFO
        "       BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to parental control."
    REVISION      "201407290000Z"
    DESCRIPTION
        "Fixed copyright header date."
    REVISION      "201401080000Z"
    DESCRIPTION
        "Corrected Last-Updated, Revision and Description fields."
    REVISION      "200702050000Z"
    DESCRIPTION
        "Module description was updated.
         Compilability issues were cleaned up
         - Chronological order of revision history was corrected."
    REVISION      "200307300000Z"
    DESCRIPTION
         "Added pctlCategoryList object."    
    REVISION      "200304170000Z"
    DESCRIPTION
         "Added new objects to invoke subscription and check status."    
    REVISION      "200304040000Z"
    DESCRIPTION
         "Initial version of this MIB module."
    ::= { cableDataMgmtMIBObjects 8 }
    
pctlService OBJECT IDENTIFIER ::= { parentalControlMgmt 1 }

pctlSubscriptionURL OBJECT-TYPE
    SYNTAX      DisplayString
    MAX-ACCESS  read-write
    STATUS      current
    DESCRIPTION
        "Identifies an internet URL which the subscriber will be directed when
         he chooses to subscribe to the parental control service."
    ::= { pctlService 1 }

pctlServiceModel OBJECT-TYPE
    SYNTAX      INTEGER {
                none(0),
                cerberianCMR(1),
                cerberianADR(2),
                rulespace(3)
    }
    MAX-ACCESS  read-write
    STATUS      current
    DESCRIPTION
        "Identifies the service model used for parental control.  If set to
         none(0), parental control will be disabled."
    ::= { pctlService 2 }
    
pctlServicePrimaryURL OBJECT-TYPE
    SYNTAX      DisplayString
    MAX-ACCESS  read-write
    STATUS      current
    DESCRIPTION
        "Identifies an internet URL which will be used as the primary parental
         control server."
    ::= { pctlService 3 }
    
pctlServiceSecondaryURL OBJECT-TYPE
    SYNTAX      DisplayString
    MAX-ACCESS  read-write
    STATUS      current
    DESCRIPTION
        "Identifies an internet URL which will be used as the primary parental
         control server.  For service providers which do not provide a 
         secondary server, this object will be empty."
    ::= { pctlService 4 }
    
pctlLicenseKey OBJECT-TYPE
    SYNTAX      OCTET STRING
    MAX-ACCESS  read-write
    STATUS      current
    DESCRIPTION
        "The parental control license key for this subscriber."
    ::= { pctlService 5 }
    
pctlLicenseExpiration OBJECT-TYPE
    SYNTAX      DateAndTime
    MAX-ACCESS  read-write
    STATUS      current
    DESCRIPTION
        "The date at which the current license key will expire.  If the key has
         no expiration, then a value of 1-1-1970 will be used."
    ::= { pctlService 6 }
    
pctlServiceSubscribeNow OBJECT-TYPE
    SYNTAX      TruthValue
    MAX-ACCESS  read-write
    STATUS      current
    DESCRIPTION
        "If set to true(1), the device will attempt to subscribe to parental
         control service based on the paramters in pctlServiceModel, 
         pctlServicePrimaryURL, pctlServiceSecondaryURL, and pctlLicenseKey.
         Results of this attempt may be retrieved from 
         pctlServiceSubscriptionStatus.
         
         If set to false(2), the device will un-subscribe from parental control
         service."
    ::= { pctlService 7 }
    
pctlServiceSubscriptionStatus OBJECT-TYPE
    SYNTAX      INTEGER {
                notAttempted(0),
                readyToSubscribe(1),
                subscribedServiceNotStarted(2),
                subscribedEstablishingService(3),
                subscribedServiceRunning(4),
                subscribedServiceError(5),
                subscriptionFailed(6),
                subscriptionExpired(7)
    }
    MAX-ACCESS  read-only
    STATUS      current
    DESCRIPTION
        "Indicates the status of the last parental control subscription attempt.
         If no attempt has been made, this object will return notAttempted(0).
         If a subscription exchange is currently in progress, inProgress(1) will
         be returned.  A successful subscription attempt will result in a value
         of successful(2), and a failed subscription attempt will result in a
         value of failure(3)."
    ::= { pctlService 8 }
    
pctlCategoryList OBJECT-TYPE
    SYNTAX      OCTET STRING (SIZE(0..1024))
    MAX-ACCESS  read-write
    STATUS      current
    DESCRIPTION
        "Identifies the list of currently available parental control 
         categories."
    ::= { pctlService 9 }
    
END
