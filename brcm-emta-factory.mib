--****************************************************************************
--
-- Copyright (c) 2002-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-emta-factory.mib
--    Author:   Kevin O'Neal
--    Creation Date: 23-august-2002
--
--****************************************************************************
--    Description:
--
--         private MIB for EMTA factory
--
--****************************************************************************
--    Revision History:
--
--****************************************************************************

BRCM-EMTA-FACTORY-MIB DEFINITIONS ::= BEGIN

IMPORTS
    MODULE-IDENTITY,
    OBJECT-TYPE
        FROM SNMPv2-SMI
    TruthValue
        FROM SNMPv2-TC
    cableDataFactory
        FROM BRCM-CABLEDATA-FACTORY-MIB;
                
emtaFactory MODULE-IDENTITY
    LAST-UPDATED "201412100000Z"
    ORGANIZATION "Broadcom Corporation"
    CONTACT-INFO
        "       BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for factory management and configuration
         of objects related to EMTA products."
    REVISION      "201412100000Z"
    DESCRIPTION
        "Added object emtaDectRFPI."
    REVISION      "201407290000Z"
    DESCRIPTION
        "Fixed copyright header date."
    REVISION      "200702050000Z"
    DESCRIPTION
        "Module description was updated. 
         Compilability issues were cleaned up: 
         - Chronological order of revision history was corrected."
    REVISION      "200511140000Z"
    DESCRIPTION
        "Changed description clause for objects emtaTelephonyRootCertificate
         and emtaManufacturerCertificate."      
    REVISION      "200506280000Z"
    DESCRIPTION
        "Added object emtaDynamicLoadBalancingEnabled."     
    REVISION      "200506140000Z"
    DESCRIPTION
        "Added object emtaHighVoltageRingEnabled."        
    REVISION      "200403240000Z"
    DESCRIPTION
        "Changed behavior of emtaDevPrivKeyModulus and 
         emtaDevPrivKeyExponent objects to return a CRC32 of the
         data when read rather than the data itself for security reasons."        
    REVISION      "200208230000Z"
    DESCRIPTION
        "Initial version of this MIB module."
    ::= { cableDataFactory 6 }

-- emtaFactoryBase: miscellaneous control/state objects for factory mode    
emtaFactoryBase OBJECT IDENTIFIER ::= { emtaFactory 1 }

emtaHighVoltageRingEnabled  OBJECT-TYPE 
    SYNTAX      TruthValue
    MAX-ACCESS  read-write
    STATUS      current
    DESCRIPTION
        "Controls the use of high voltage ringing for this device."
    ::= { emtaFactoryBase 1 }
    
emtaDynamicLoadBalancingEnabled  OBJECT-TYPE 
    SYNTAX      TruthValue
    MAX-ACCESS  read-write
    STATUS      current
    DESCRIPTION
        "Controls the use of dynamic load balancing for platforms which support
         this feature."
    ::= { emtaFactoryBase 2 }

emtaDectRFPI  OBJECT-TYPE 
    SYNTAX      OCTET STRING (SIZE (5))
    MAX-ACCESS  read-write
    STATUS      current
    DESCRIPTION
        "Controls the DECT RFPI value. The DECT RFPI size is 5 bytes long and
         can be written to using a 5 byte octet string. Reads to the DECT RFPI
         will return the 5 byte hex value."
    ::= { emtaFactoryBase 3 }

-- chFactorySecurity: Security-related factory objects
emtaFactorySecurity OBJECT IDENTIFIER ::= { emtaFactory 2 }

emtaTelephonyRootCertificate  OBJECT-TYPE 
    SYNTAX      OCTET STRING -- size?
    MAX-ACCESS  read-write
    STATUS      current
    DESCRIPTION
        "An alternate PacketCable telephony root certificate.  An alternate
         certificate is most often used during lab or certification testing.  It 
         may also be used by an operator who does not use telephony certificates
         that chain the CableLabs root certificate."
    ::= { emtaFactorySecurity 1 }

emtaManufacturerCertificate  OBJECT-TYPE 
    SYNTAX      OCTET STRING -- size?
    MAX-ACCESS  read-write
    STATUS      current
    DESCRIPTION
        "The Packetcable manufacturer certificate."
    ::= { emtaFactorySecurity 2 }

emtaDeviceCertificate  OBJECT-TYPE 
    SYNTAX      OCTET STRING -- size?
    MAX-ACCESS  read-write
    STATUS      current
    DESCRIPTION
        "The PacketCable device certificate."
    ::= { emtaFactorySecurity 3 }

emtaDevPrivKeyModulus  OBJECT-TYPE 
    SYNTAX      OCTET STRING -- size?
    MAX-ACCESS  read-write
    STATUS      current
    DESCRIPTION
        "The PacketCable private key modulus.  In order to prevent
         unauthorized discovery of the private key, when read this object
         does not return the modulus.  Instead, a CRC32 is performed over the
         modulus and the resulting 32 bit value is returned as a 4 byte octet
         string.  Note that if the modulus is empty, a CRC value of 00 00 00 00
         is returned."
    ::= { emtaFactorySecurity 4 }

emtaDevPrivKeyExponent  OBJECT-TYPE 
    SYNTAX      OCTET STRING -- size?
    MAX-ACCESS  read-write
    STATUS      current
    DESCRIPTION
        "The PacketCable private key exponent.  In order to prevent
         unauthorized discovery of the private key, when read this object
         does not return the exponent.  Instead, a CRC32 is performed over the
         exponent and the resulting 32 bit value is returned as a 4 byte octet
         string.  Note that if the exponent is empty, a CRC value of 00 00 00 00
         is returned."
    ::= { emtaFactorySecurity 5 }

END
