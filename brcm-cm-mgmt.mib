--****************************************************************************
--
-- Copyright (c) 2005-2015 Broadcom Corporation 
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cm-mgmt.mib
--    Author:   Kevin O'Neal
--    Creation Date: April 18, 2005
--
--****************************************************************************
--    Description:
--
--      private MIB for runtime (not factory) CM management
--
--****************************************************************************
--    Revision History:
--
--****************************************************************************

BRCM-CM-MGMT-MIB DEFINITIONS ::= BEGIN

IMPORTS
    MODULE-IDENTITY,
    OBJECT-TYPE,
    OBJECT-IDENTITY,
    NOTIFICATION-TYPE,
    Unsigned32,
    Counter32,
    Integer32,
    Gauge32
        FROM SNMPv2-SMI
    TruthValue,
    DisplayString,
    RowStatus,
    StorageType
        FROM SNMPv2-TC
    OBJECT-GROUP,
    MODULE-COMPLIANCE,
    NOTIFICATION-GROUP
        FROM SNMPv2-CONF
    IANAifType
        FROM IANAifType-MIB
    ifPhysAddress,
    ifIndex
        FROM IF-MIB
    docsDevEvLevel,
    docsDevEvId,
    docsDevEvText
        FROM DOCS-CABLE-DEVICE-MIB
    docsIfCmCmtsAddress,
    docsIfDocsisBaseCapability,
    docsIfCmStatusDocsisOperMode,
    docsIfCmStatusModulationType,
    TenthdBmV
        FROM DOCS-IF-MIB
    AmplitudeData
        FROM DOCS-IF3-MIB
    cableDataMgmtMIBObjects
        FROM BRCM-CABLEDATA-MGMT-MIB;

cablemodemMgmt MODULE-IDENTITY
    LAST-UPDATED "201501220000Z"
    ORGANIZATION "Broadcom Corporation"
    CONTACT-INFO
        "   BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management of cablemodem devices."
    REVISION      "201501220000Z"
    DESCRIPTION
        "Added cmObsoleteGroup which includes cmIpProvisioningMode and cmChannelBondingPowerSaveStrategy."
    REVISION      "201407290000Z"
    DESCRIPTION
        "Fixed copyright header date."
    REVISION      "201407180000Z"
    DESCRIPTION
        "Added cmHalInterfaces object."
    REVISION      "201407110000Z"
    DESCRIPTION
        "Added cmDocsis30NonVolEnabledFeatures object."
    REVISION      "201407010000Z"
    DESCRIPTION
        "Fixed smilint errors and cleaned up whitespace."
    REVISION      "201401080000Z"
    DESCRIPTION
        "Changed cmDownstreamNumChannels from 0..16 to 0..32 to support 32 downstream channels."
    REVISION      "201308260000Z"
    DESCRIPTION
        "Added group cmSpectrumAnalysisReferenceSpectrum."
    REVISION      "201304110000Z"
    DESCRIPTION
        "Added OBJECT-IDENTITY to the imports section."
    REVISION      "201304030000Z"
    DESCRIPTION
        "Fix cmIpOperMode in MODULE-COMPLIANCE cmBaseGroup."
    REVISION      "201302180000Z"
    DESCRIPTION
        "Added cmIpOperMode object."
    REVISION      "201209240000Z"
    DESCRIPTION
        "Added new objects cmDownstreamNumChannels, cmUpstreamNumChannels, and
         cmUpstreamMtcMode."
    REVISION      "201208020000Z"
    DESCRIPTION
        "Added new objects to cmSpectrumAnalysis group to provide additional
        control over spectrum measurement parameters."
    REVISION      "201206140000Z"
    DESCRIPTION
        "Obsoleted object cmIpProvisioningMode"
    REVISION      "201205090000Z"
    DESCRIPTION
        "Added objects cmSpectrumAnalysisEnable and
        cmSpectrumAnalysisInactivityTimeout."
    REVISION      "201205010000Z"
    DESCRIPTION
        "Updated description of cmChannelBondingPowerSaveStrategy object and
         changed its default value to cmStatusWith1x1Fallback."
    REVISION      "201112060000Z"
    DESCRIPTION
        "Introduced new group cmSpectrumAnalysis."
    REVISION      "201111210000Z"
    DESCRIPTION
        "Introduced new enumerated value of cmStatusWith1x1Fallback for the
         cmChannelBondingPowerSaveStrategy object."
    REVISION      "201111080000Z"
    DESCRIPTION
        "Restored support for autonomous1x1 value for
         cmChannelBondingPowerSaveStrategy, but with new behavior."
    REVISION      "201110280000Z"
    DESCRIPTION
        "Added new node cmBfcEvents under which CM specific IDs for the
         bfcEventTable may be defined.  First such event is cmConfigFileEvent."
    REVISION      "201107110000Z"
    DESCRIPTION
        "Added object cmChannelBondingCapability."
    REVISION      "201104260000Z"
    DESCRIPTION
        "Added object cmExtendedUsTxPowerCapability."
    REVISION      "201104130000Z"
    DESCRIPTION
        "Added object cmOverrideUcdMaxBurst."
    REVISION      "201008130000Z"
    DESCRIPTION
        "Added object cmStartDsidLearningWhenDccRspArriveSent."
    REVISION      "200911090000Z"
    DESCRIPTION
        "Obsoleted autonomous1x1 value and added disabled value for
         cmChannelBondingPowerSaveStrategy object."
    REVISION      "200911030000Z"
    DESCRIPTION
        "Added object cmUcastDsidAllowNonZeroInitialPsn."
    REVISION      "200910190000Z"
    DESCRIPTION
        "Added object cmForwardingHwAssistEnable."
    REVISION      "200909090000Z"
    DESCRIPTION
        "Added objects cmDsChanInfoTuner and cmDsChanInfoTunerChannel."
    REVISION      "200908260000Z"
    DESCRIPTION
        "Added cmServiceQueueTable."
    REVISION      "200908070000Z"
    DESCRIPTION
        "Added cmChannelBondingUpstreamTable."
    REVISION      "200907310000Z"
    DESCRIPTION
        "Added cmIpProvisioningMode object."
    REVISION      "200906180000Z"
    DESCRIPTION
        "Added cmChannelBondingPowerSaveStrategy object."
    REVISION      "200904010000Z"
    DESCRIPTION
        "Added cmDownstreamChannelInfoTable with cmDsChanInfoCodewordErrorRate
        and cmDsChanInfoMeanSquareError objects."
    REVISION      "200806120000Z"
    DESCRIPTION
        "Added conformances & compliances."
    REVISION      "200708140000Z"
    DESCRIPTION
        "Added node cmEmbeddedDevices for location of other modules which
         control CM features specific only to embedded devices (such as
         EMTA, EPS, etc)."
    REVISION      "200702050000Z"
    DESCRIPTION
        "Compilability issues were cleaned up:
         - Chronological order of revision history was corrected.
         - Missing imports were added.
         - Case of object CmHostIpFilterEntry was corrected.
         - Defval syntax for object cmHostIpFilterInterfaces was corrected."
    REVISION      "200701040030Z"
    DESCRIPTION
        "Added cmMDDTimeoutTrap notification."
    REVISION      "200701040000Z"
    DESCRIPTION
        "Added cmNotification group and cmDocsDevEventTrap notification."
    REVISION      "200611030000Z"
    DESCRIPTION
        "Added cmHostIpFilterTable object."
    REVISION      "200610060000Z"
    DESCRIPTION
        "Added cmTodRefreshInterval object."
    REVISION      "200605030000Z"
    DESCRIPTION
        "Added cmResetFactoryDefaults object."
    REVISION      "200603070000Z"
    DESCRIPTION
        "Added cmCpeInterface object."
    REVISION      "200510280000Z"
    DESCRIPTION
        "Added cmDsdExtendedRetryEnable object."
    REVISION      "200505090000Z"
    DESCRIPTION
        "Added cmMiniFirewallEnable object."
    REVISION      "200504180000Z"
    DESCRIPTION
        "Initial version of this MIB module."
    ::= { cableDataMgmtMIBObjects 2 }

cmMgmtBase OBJECT IDENTIFIER ::= { cablemodemMgmt 1 }

cmNumLLCFiltersSupported OBJECT-TYPE
    SYNTAX      Unsigned32
    MAX-ACCESS  read-only
    STATUS      current
    DESCRIPTION
        "Indicates the number of entries in the docsDevFilterLLCTable
         which can be supported on this particular device under current
         operating conditions.  Note that this is a conservative estimate and
         that the device will generally be able to support more filters than
         this number returns.

         Further note that this number reflects the number of filters supported
         if the docsDevFilterIpTable is also simultaneously populated with the
         number of filters returned by cmNumIpFiltersSupported.  If no IP
         filters are configured then the device can be expected to support
         double the number of LLC filters indicated by this object."
    REFERENCE
         "docsDevFilterLLCTable from DOCS-CABLE-DEVICE-MIB"
    ::= { cmMgmtBase 1 }

cmNumIpFiltersSupported OBJECT-TYPE
    SYNTAX      Unsigned32
    MAX-ACCESS  read-only
    STATUS      current
    DESCRIPTION
        "Indicates the number of entries in the docsDevFilterIpTable
         which can be supported on this particular device under current
         operating conditions.  Note that this is a conservative estimate and
         that the device will generally be able to support more filters than
         this number returns.

         Further note that this number reflects the number of filters supported
         if the docsDevFilterLLCTable is also simultaneously populated with the
         number of filters returned by cmNumLLCFiltersSupported.  If no LLC
         filters are configured then the device can be expected to support
         double the number of IP filters indicated by this object."
    REFERENCE
         "docsDevFilterIpTable from DOCS-CABLE-DEVICE-MIB"
    ::= { cmMgmtBase 2 }

cmMiniFirewallEnable OBJECT-TYPE
    SYNTAX      TruthValue
    MAX-ACCESS  read-write
    STATUS      current
    DESCRIPTION
        "Specifies whether the CM mini-firewall will be enabled, provided the
         mini-firewall feature is supported.  If the feature is not supported,
         this object will always report false(2) and an attempt to set it to
         true(1) will be rejected with an inconsistentValue error."
    ::= { cmMgmtBase 3 }

cmDsdExtendedRetryEnable OBJECT-TYPE
    SYNTAX      TruthValue
    MAX-ACCESS  read-write
    STATUS      current
    DESCRIPTION
        "Specifies the behavior of the CM with regards to retrying DSD requests
         when no reply is received.  If set to true(1), the CM will continue
         to retry the request until a reply is received or roughly one hour
         of time has passed.  If set to false(2), the CM will stop retrying
         after three retries as required by the DOCSIS specification.  Note
         that this setting is not persistent across reboot."
    ::= { cmMgmtBase 4 }

cmCpeInterface OBJECT-TYPE
    SYNTAX      IANAifType
    MAX-ACCESS  read-write
    STATUS      current
    DESCRIPTION
        "For designs which are not capable of supporting multiple CPE interfaces
         simultaneously, this object specifies the interface which will be
         used as a CPE interface.  Typical settings for such a design would
         include ethernet(6) and usb(160).  For designs which are capable of
         supporting multiple CPE interfaces, this object will always return
         other(1)."
    ::= { cmMgmtBase 5 }

cmResetFactoryDefaults OBJECT-TYPE
    SYNTAX      TruthValue
    MAX-ACCESS  read-write
    STATUS      current
    DESCRIPTION
        "Setting this object to true(1) will cause the device to reset all
         non-volatile settings to their factory default state, and the device
         to be rebooted.  Note that only dynamic settings will be affected;
         permanent settings (MAC addresses, etc) will remain unchanged.  When
         read, this object always returns false(2)."
    ::= { cmMgmtBase 6 }

cmTodRefreshInterval OBJECT-TYPE
    SYNTAX      Unsigned32
    UNITS       "hours"
    MAX-ACCESS  read-write
    STATUS      current
    DESCRIPTION
        "This object controls the length of time between periodic updates
         of system time by way of a Time of Day (ToD) refresh.  If set to
         0, time of day will not be refreshed.  Note that in order to comply
         with the DOCSIS requirements for ToD periodicity, a value of 0 should
         be used for this object."
    REFERENCE
         "Time Protocol (RFC-868)"
    ::= { cmMgmtBase 7 }

--
-- The CM Downstream Parameters Table
--

cmDownstreamChannelInfoTable OBJECT-TYPE
    SYNTAX      SEQUENCE OF CmDownstreamChannelInfoEntry
    MAX-ACCESS  not-accessible
    STATUS      current
    DESCRIPTION
        "A table describing the characteristics of each downstream channel.  An
         entry exists in this table for each entry in the ifTable with an
         ifType value of docsCableDownstream (128)."
    ::= { cmMgmtBase 8 }

cmDownstreamChannelInfoEntry OBJECT-TYPE
    SYNTAX      CmDownstreamChannelInfoEntry
    MAX-ACCESS  not-accessible
    STATUS      current
    DESCRIPTION
        "An entry describing the attributes of a single downstream channel."
    INDEX  { ifIndex }
    ::= { cmDownstreamChannelInfoTable 1 }

CmDownstreamChannelInfoEntry ::=
    SEQUENCE {
             cmDsChanInfoCodewordErrorRate      DisplayString,
             cmDsChanInfoMeanSquareError        DisplayString,
             cmDsChanInfoTuner                  Integer32,
             cmDsChanInfoTunerChannel           Integer32
             }

cmDsChanInfoCodewordErrorRate OBJECT-TYPE
    SYNTAX      DisplayString
    MAX-ACCESS  read-only
    STATUS      current
    DESCRIPTION
        "Downstream Codeword Error Rate. (Errored Codewords / Total CodeWords)"
    ::= { cmDownstreamChannelInfoEntry 1 }

cmDsChanInfoMeanSquareError OBJECT-TYPE
    SYNTAX      DisplayString
    MAX-ACCESS  read-only
    STATUS      current
    DESCRIPTION
        "Downstream Mean Square Error"
    ::= { cmDownstreamChannelInfoEntry 2 }

cmDsChanInfoTuner OBJECT-TYPE
    SYNTAX      Integer32 (0|1..4)
    MAX-ACCESS  read-only
    STATUS      current
    DESCRIPTION
        "Indicates the tuner to which this downstream channel is mapped.  A
         value of 0 is a special case which indicates that this channel is not
         mapped to any tuner - this would generally only be the case under
         unusual circumstances such as very shortly after bootup before
         scanning has started."
    ::= { cmDownstreamChannelInfoEntry 3 }

cmDsChanInfoTunerChannel OBJECT-TYPE
    SYNTAX      Integer32 (-2..2)
    MAX-ACCESS  read-only
    STATUS      current
    DESCRIPTION
        "Indicates which channel of the tuner identified by cmDsChanInfoTuner
         is mapped to this downstream channel.  Values are defined as offsets
         from the center channel of the tuner, which is represented by a value
         of 0 for this object.

         Note that allowable values for this object are constrained by the
         number of channels that this tuner is capable of spanning.  A value of
         0 - denoting the exact center channel - is only valid if the number of
         channels spanned by the tuner is odd.  For tuners which span an even
         number of channels, a value of 0 will never be reported.  Single
         channel tuners will always report a value of 0.

         If cmDsChanInfoTuner has a value of 0 (not associated) then the value
         returned by this object has no meaning; in this case a value of 0
         will be returned."
    ::= { cmDownstreamChannelInfoEntry 4 }

cmIpProvisioningMode OBJECT-TYPE
    SYNTAX      INTEGER {
                mdd(0),
                ipV4Only(1),
                ipV6Only(2),
                apm(3),
                dualStack(4)
    }
    MAX-ACCESS  read-write
    STATUS      obsolete
    DESCRIPTION
        "This object has been obsoleted in favor of docsIf3CmMdCfgIpProvMode
         from the DOCS-IF3-MIB.

         The value of this object determines the mode used by the CM for IP
         provisioning.

         If set to the default value of mdd(0), the CM will comply with the
         DOCSIS 3.0 specification and use the mode identified in the IP
         provisioning mode field of the MDD message received from the CMTS.

         If set to any other value, the CM will ignore the IP provisioning mode
         field of the MDD message and use the mode specified by this object
         instead.

         If the DOCSIS config file contains a TLV which changes the value of
         this object from its current value, the CM will abandon its current IP
         settings and restart the IP provisioning and registration process using
         the new mode.  Setting this object using SNMP does not cause a
         restart; in the case of an SNMP set, the new mode will take effect
         the next time the CM registers with a CMTS.

         Note that this object may also be used to invoke IPv6 or dual-stack
         operation when using a pre-DOCSIS 3.0 CMTS, provided the network
         hosting the CM is IPv6 capable.

         Further note that a CM which does not support IPv6 will always report
         ipV4Only(1) for this object, and an attempt to set the object to any
         other value will be rejected with an inconsistentValue error.

         If this object is set to a value which is incompatible with the
         capabilities of the associated CMTS or network, then IP provisioning
         may fail.  This setting is persistent across reboots."
    REFERENCE
        "DOCSIS 3.0 MAC and Upper Layer Protocols Interface Specification
         CM-SP-MULPIv3.0-I19-120809, sections 6.4.28.1.5 'IP Initialization
         Parameters TLV' and 10.2.5 'Establishing IP Connectivity'"
    DEFVAL { mdd }
    ::= { cmMgmtBase 9 }

cmServiceQueueTable OBJECT-TYPE
    SYNTAX      SEQUENCE OF CmServiceQueueEntry
    MAX-ACCESS  not-accessible
    STATUS      current
    DESCRIPTION
        "This table describes attributes of each upstream service queue on
         a CM."
    ::= { cmMgmtBase 10 }

cmServiceQueueEntry OBJECT-TYPE
    SYNTAX      CmServiceQueueEntry
    MAX-ACCESS  not-accessible
    STATUS      current
    DESCRIPTION
        "Describes the attributes of a single service queue.  An entry exists
         in this table exists for each service queue.  The ifIndex refers to
         the entry in the ifTable with an ifType value of
         docsCableMaclayer(127)."
    INDEX { ifIndex, cmServiceQueueId }
    ::= { cmServiceQueueTable 1 }

CmServiceQueueEntry ::=
    SEQUENCE    {
                cmServiceQueueId                 Integer32,
                cmServiceQueueMaxQueueDepth      Gauge32,
                cmServiceQueueCurrentQueueDepth  Gauge32
    }

cmServiceQueueId OBJECT-TYPE
     SYNTAX      Integer32 (1..16383)
     MAX-ACCESS  not-accessible
     STATUS      current
     DESCRIPTION
         "Identifies a service queue for upstream bandwidth.  This value is
          equal to the SID for this service queue."
     ::= { cmServiceQueueEntry 1 }

cmServiceQueueMaxQueueDepth  OBJECT-TYPE
    SYNTAX      Gauge32
    MAX-ACCESS  read-only
    STATUS      current
    DESCRIPTION
        "Indicates the maximum number of packets which can be enqueued on this
         service queue.

         Note that for DOCSIS 3.0 devices operating in QoS mode, max queue depth
         is now specified in terms of bytes, not packets.  Thus, for such a
         configuration, this object will return 0.  The maximum queue depth for
         such a configuration may be read from docsQosServiceFlowBufferSize."
    ::= { cmServiceQueueEntry 2 }

cmServiceQueueCurrentQueueDepth  OBJECT-TYPE
    SYNTAX      Gauge32
    MAX-ACCESS  read-only
    STATUS      current
    DESCRIPTION
        "Indicates the number of packets currently enqueued on this service
         queue."
    ::= { cmServiceQueueEntry 3 }

cmForwardingHwAssistEnable OBJECT-TYPE
    SYNTAX      TruthValue
    MAX-ACCESS  read-write
    STATUS      current
    DESCRIPTION
        "Specifies whether the hardware forwarding assist engine is enabled,
         for devices which support such assistance.

         For devices which do not have hardware forwarding assist support,
         this object will always return false(2), and an attempt to set this
         object to true(1) will result in an inconsistentValue error."
    DEFVAL { true }
    ::= { cmMgmtBase 11 }

cmOverrideUcdMaxBurst OBJECT-TYPE
    SYNTAX      Integer32 (0..255)
    UNITS       "mini-slots"
    MAX-ACCESS  read-write
    STATUS      current
    DESCRIPTION
        "This object may be used to override the max burst value specified in
         the burst descriptor corresponding to the long data grant IUC from the
         upstream channel descriptor (UCD).

         If set to the default value of 0, the CM will conform to the DOCSIS
         specification requirements and abide by the max burst values as
         specified in the UCD.

         If set to any other value, the CM will limit burst sizes to either the
         value specified by this object or the UCD specified value, whichever
         is larger.

         Setting this object to a value of 255 effectively means that the burst
         size will be unlimited.  This setting will maximize upstream
         throughput.

         Note that the value of this object has no effect on burst limitations
         as configured by service flow parameter sets."
     REFERENCE
        "Data-Over-Cable Service Interface Specifications Docsis 3.0: Physical
         Layer Specification CM-SP-PHYv3.0-I09-101008, Table 6-11"
     DEFVAL { 0 }
    ::= { cmMgmtBase 12 }

cmExtendedUsTxPowerCapability  OBJECT-TYPE
    SYNTAX      Integer32 (0|205..244)
    UNITS       "quarter dBmV"
    MAX-ACCESS  read-write
    STATUS      current
    DESCRIPTION
         "Specifies the maximum extended upstream transmit power of which this
          device is capable.  A value of zero indicates that the device has no
          extended upstream power capability.  The value specified in this
          object will be advertised in TLV 5.40 of the CM's modem capability
          message."
    REFERENCE
         "Data-Over-Cable Service Interface Specifications DOCSIS 3.0 MAC and
          Upper Layer Protocols Interface Specification
          CM-SP-MULPIv3.0-I19-120809 section 6.4.28.1.15 'Extended Upstream
          Transmit Power Support'"
    ::= { cmMgmtBase 13 }

cmIpOperMode OBJECT-TYPE
    SYNTAX      INTEGER {
                unknown(0),
                ipV4(1),
                ipV6(2),
                dualStack(3)
    }
    MAX-ACCESS  read-only
    STATUS      current
    DESCRIPTION
         "The value of this object is the operational mode used by the CM
         for its IP stack(s). This can come from non-vol, the MDD, or the
         MIB object docsIf3CmMdCfgIpProvMode from the DOCS-IF3-MIB.

         This object reports the actual operation of the IP stacks rather
         than the provisioned, intended, operation. If the stack(s) in an
         undetermined state, perhaps waiting for an MDD, then unknown(0)
         is reported. If one address type is operational, then either
         ipV4(1) or ipV6(2) is reported, as appropriate. If both address
         types are operational, then dualStack(3) is reported."
    REFERENCE
        "DOCSIS 3.0 MAC and Upper Layer Protocols Interface Specification
         CM-SP-MULPIv3.0-I19-120809, sections 6.4.28.1.5 'IP Initialization
         Parameters TLV' and 10.2.5 'Establishing IP Connectivity'"
    DEFVAL { ipV4 }
    ::= { cmMgmtBase 14 }

cmDocsis30NonVolEnabledFeatures OBJECT-TYPE
    SYNTAX      BITS {
                    ipv6(0),
                    overrideMdd(1),
                    rptEaeCap(2),
                    sgDiscFailMode(3),
                    mpRegReqFormat(4),
                    mcastDsidFwdDisable(5),
                    eaeOffset(6),
                    dbcHmacMismatchIgnore(7),
                    forceD30ModemCaps(8),
                    noTccUcd(9),
                    suppressTotalSidCluster(10),
                    useCbcTekDecryption(11),
                    noDrw(12),
                    noD30VersionModemCapsIfNoMdd(13),
                    dsidPsnWorkaround(14),
                    dsBondingCapability(15),
                    usBondingCapability(16),
                    noNrg1x1(17)
    }
    MAX-ACCESS  read-only
    STATUS      current
    DESCRIPTION
         "Returns the enabled features set in the DOCSIS 3.0 non-vol
          as a bitmask."
    ::= { cmMgmtBase 15 }

cmHalInterfaces OBJECT-TYPE
    SYNTAX      BITS {
                    docsisCmHal(0),
                    ethernetHal(1),
                    hpnaHal(2),
                    usbHal(3),
                    ipStack1Hal(4),
                    ipStack2Hal(5),
                    ipStack3Hal(6),
                    ipStack4Hal(7),
                    davicHal(8),
                    pciHal(9),
                    bluetoothHal(10),
                    wifi80211Hal(11),
                    packetGeneratorHal(12),
                    ipStack5Hal(13),
                    ipStack6Hal(14),
                    ipStack7Hal(15),
                    ipStack8Hal(16),
                    wanEthernetHal(17),
                    scbHal(18),
                    itcHal(19),
                    mocaHal(20),
                    ipStack9Hal(21),
                    ipStack10Hal(22),
                    ipStack11Hal(23),
                    ipStack12Hal(24),
                    ipStack13Hal(25),
                    ipStack14Hal(26),
                    ipStack15Hal(27),
                    ipStack16Hal(28)
    }
    MAX-ACCESS  read-only
    STATUS      current
    DESCRIPTION
        "Returns the current interfaces as reported by /non/hal/interfaces
         as a bitmask."
    ::= { cmMgmtBase 16 }

cmFilter OBJECT IDENTIFIER ::= { cablemodemMgmt 2 }

cmHostIpFilterTable OBJECT-TYPE
    SYNTAX      SEQUENCE OF CmHostIpFilterEntry
    MAX-ACCESS  not-accessible
    STATUS      current
    DESCRIPTION
        "The table of IP filters to be applied to traffic originating from
         or destined to this device.  The fields in this table are loosely
         based on a subset of the fields in the docsDevFilterIpTable as defined
         in the DOCS-CABLE-DEVICE-MIB.  The key difference is that the filters
         described by the cmHostIpFilterTable are not applied to bridged
         traffic, but rather to traffic which is sent from or received by the
         cablemodem itself, acting in a role as a host.

         This table may be used to restrict certain IP traffic (eg SNMP,
         TFTP, telnet, etc.) from being accessible via the CPE and / or HFC
         interfaces.  Note that all filters will be applied to all IP
         addresses associated with this host.

         Caution must be exercised in the use of this table.  For example, it
         is possible to render the device unmanageable if SNMP is prohibited
         over both CPE and CM interfaces."
    REFERENCE
         "docsDevFilterIpTable from the DOCS-CABLE-DEVICE-MIB"
    ::= { cmFilter 1 }

cmHostIpFilterEntry OBJECT-TYPE
    SYNTAX      CmHostIpFilterEntry
    MAX-ACCESS  not-accessible
    STATUS      current
    DESCRIPTION
        "An instance of an IP filter.  Entries in the cmHostIpFilterTable are
         created and deleted using the cmHostIpFilterStatus object.

         Each filter describes a set of criteria against which each IP packet
         will be compared.  Any packet which matches the filter will be
         discarded.

         Note that these filters are not applied to bridged traffic, only
         to traffic which is sent from or received by the cablemodem itself."
    INDEX   { cmHostIpFilterIndex }
    ::= { cmHostIpFilterTable 1 }

CmHostIpFilterEntry ::=
    SEQUENCE    {
                cmHostIpFilterIndex                 Integer32,
                cmHostIpFilterStatus                RowStatus,
                cmHostIpFilterStorageType           StorageType,
                cmHostIpFilterMatches               Counter32,
                cmHostIpFilterInterfaces            BITS,
                cmHostIpFilterDirection             INTEGER,
                cmHostIpFilterDestPortLow           Integer32,
                cmHostIpFilterDestPortHigh          Integer32
    }

cmHostIpFilterIndex OBJECT-TYPE
    SYNTAX      Integer32 (1..2147483647)
    MAX-ACCESS  not-accessible
    STATUS      current
    DESCRIPTION
        "Identifies the instance number of this conceptual row."
    ::= { cmHostIpFilterEntry 1 }

cmHostIpFilterStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         cmHostIpFilterStatus column is 'notReady'.

         In particular, a newly created row cannot be made active until the
         corresponding instances of cmHostIpFilterDestPortLow and
         cmHostIpFilterDestPortHigh have been set.

         Only filters with a status of active(1) will be applied."
    ::= { cmHostIpFilterEntry 2 }

cmHostIpFilterStorageType OBJECT-TYPE
    SYNTAX      StorageType
    MAX-ACCESS  read-create
    STATUS      current
    DESCRIPTION
        "The storage type for this conceptual row.  Conceptual rows having the
         value 'permanent' need not allow write-access to any columnar objects
         in the row."
    DEFVAL { volatile }
    ::= { cmHostIpFilterEntry 3 }

cmHostIpFilterMatches OBJECT-TYPE
    SYNTAX      Counter32
    MAX-ACCESS  read-only
    STATUS      current
    DESCRIPTION
        "Counts the number of times this filter was matched."
    ::= { cmHostIpFilterEntry 4 }

cmHostIpFilterInterfaces OBJECT-TYPE
    SYNTAX      BITS {
                cpe(0), -- All CPE interfaces
                cm(1)   -- HFC interface
    }
    MAX-ACCESS  read-create
    STATUS      current
    DESCRIPTION
        "Identifies the interfaces to which this filter applies."
    DEFVAL { { cpe } }
    ::= { cmHostIpFilterEntry 5 }

cmHostIpFilterDirection OBJECT-TYPE
    SYNTAX      INTEGER {
                inbound(1),
                outbound(2),
                both(3)
    }
    MAX-ACCESS  read-create
    STATUS      current
    DESCRIPTION
        "Determines whether the filter is applied to inbound(1) traffic,
         outbound(2) traffic, or traffic in both(3) directions."
    DEFVAL { inbound }
    ::= { cmHostIpFilterEntry 6 }

cmHostIpFilterDestPortLow OBJECT-TYPE
    SYNTAX      Integer32 (0..65535)
    MAX-ACCESS  read-create
    STATUS      current
    DESCRIPTION
        "The inclusive lower bound of the transport-layer destination
         port range that is to be matched."
    ::= { cmHostIpFilterEntry 7 }

cmHostIpFilterDestPortHigh OBJECT-TYPE
    SYNTAX      Integer32 (0..65535)
    MAX-ACCESS  read-create
    STATUS      current
    DESCRIPTION
        "The inclusive upper bound of the transport-layer destination
         port range that is to be matched."
    ::= { cmHostIpFilterEntry 8 }

cmChannelBonding OBJECT IDENTIFIER ::= { cablemodemMgmt 3 }

cmChannelBondingPowerSaveStrategy OBJECT-TYPE
    SYNTAX      INTEGER {
                disabled(-1),
                cmStatus(0),
                autonomous1x1(1),
                cmStatusWith1x1Fallback(2)
    }
    MAX-ACCESS  read-write
    STATUS      deprecated
    DESCRIPTION
        "This object has been deprecated in favor of the
         powerMgmtCmChannelBondingStrategy object from the BRCM-POWER-MGMT-MIB.

         Determines the channel bonding transition strategy used when the CM
         enters reduced power mode due to transition to battery power or thermal
         event.

         For the purposes of this MIB description, 'reduced power mode' means a
         mode of operation in which modem features are intentionally disabled as
         a response to a trigger event.  It is not related to measures which
         may be employed during normal operation with the goal of improving
         overall energy efficiency.

         When set to a value of disabled(-1), the modem will not change the
         channel bonding configuration in response to a transition to reduced
         power mode.  The device will continue to operate in the bonding
         configuration that was in effect at the time the modem entered
         reduced power mode.

         When set to cmStatus(0), the CM will conform to DOCSIS 3.0 requirements
         by dispatching a CM-STATUS message to the CMTS with a type code of 9,
         'CM operating on battery backup', indicating a transition to battery
         mode.  The CMTS is then expected to initiate a DBC transaction which
         will reduce the number of channels used by the CM.

         Note that the 'battery backup' event code is used for either type of
         trigger, because the CM-STATUS event set does not include message codes
         for other reduced power events.

         The value of autonomous1x1(1) is used when the CM is operating in an
         environment in which the CMTS does not respond to CM-STATUS messaging
         for type code 9.

         In this mode, upon transition to reduced power mode, the CM will
         re-initialize the MAC and re-register, reporting a value of 0 for
         the Multiple Transmit Channel Support modem capability and a value of 0
         for the Multiple Receive Channel Support modem capability. This disables
         both downstream channel bonding and Multiple Transmit Channel Mode.
         The CM will then register in DOCSIS 2.0 1x1 mode, resulting in reduced
         power consumption.

         Note that if a critical data service (such as a telephone call in the
         case of a device which includes an eMTA) is in progress, the MAC
         re-init will be deferred until the critical operation completes.  Upon
         transition back to full power mode, the CM will again re-init the MAC,
         this time advertising Multiple Transmit Channel support and Multiple
         Receive Channel Support to the extent that the device is capable.
         Again, the re-init may be deferred if necessary to avoid interruption
         of a critical data service.

         The default value of cmStatusWith1x1Fallback(2) combines the cmStatus
         mode with a fallback to autonomous1x1 mode.  Upon transition to reduced
         power mode, the CM will dispatch a CM-STATUS message to the CMTS in an
         attempt to change to 1x1 mode according to standard DOCSIS mechanisms.
         If, after 30 seconds, the CM has not transitioned to 1x1 mode then the
         CM will re-initialize the MAC and re-register in 1x1 mode as described
         above."
    DEFVAL { cmStatusWith1x1Fallback }
    ::= { cmChannelBonding 1 }

cmChannelBondingUpstreamTable OBJECT-TYPE
    SYNTAX      SEQUENCE OF CmChannelBondingUpstreamEntry
    MAX-ACCESS  not-accessible
    STATUS      current
    DESCRIPTION
        "A table defining management extensions for DOCSIS 3.0 upstream channels."
    ::= { cmChannelBonding 2 }

cmChannelBondingUpstreamEntry OBJECT-TYPE
    SYNTAX      CmChannelBondingUpstreamEntry
    MAX-ACCESS  not-accessible
    STATUS      current
    DESCRIPTION
        "An entry describing the characteristics of a single upstream channel.
         An entry exists in this table for each entry in the ifTable with an
         ifType value of docsCableUpstream(129)."
    INDEX  { ifIndex }
    ::= { cmChannelBondingUpstreamTable 1 }

CmChannelBondingUpstreamEntry ::=
    SEQUENCE {
             cmBondedUsDRWTop           TenthdBmV,
             cmBondedUsDRWBottom        TenthdBmV,
             cmBondedUsDRWViolations    Counter32
    }

cmBondedUsDRWTop OBJECT-TYPE
    SYNTAX      TenthdBmV
    MAX-ACCESS  read-only
    STATUS      current
    DESCRIPTION
        "This object reports an absolute power level which is the top of the
         dynamic range window for this upstream channel.

         This value is calculated by applying the value for Pload_min_set,
         as specified by the dynamic range window upper edge TLV in the RNG-RSP
         or TCC encodings, to the max allowable power level (Phi) of this
         particular channel.

         This object will return zero if no dynamic range window upper edge TLV
         has been specified in either the RNG-RSP or TCC encodings."
    REFERENCE
        "DOCSIS 3.0 MAC and Upper Layer Protocols Interface Specification
         CM-SP-MULPIv3.0-I19-120809, sections 8.3.3 'Dynamic Range Window' and
         C.1.5.1.9 'Dynamic Range Window'"
    ::= { cmChannelBondingUpstreamEntry 1 }

cmBondedUsDRWBottom OBJECT-TYPE
    SYNTAX      TenthdBmV
    MAX-ACCESS  read-only
    STATUS      current
    DESCRIPTION
        "This object reports an absolute power level which is the bottom of
         the dynamic range window for this upstream channel.

         This value is calculated by applying the value for Pload_min_set,
         as specified by the dynamic range window upper edge TLV in the RNG-RSP
         or TCC encodings, and the fixed 12dB range of transmit power levels
         defined by the DRW, to the max allowable power level (Phi) of this
         particular channel.

         This object will return zero if no dynamic range window upper edge TLV
         has been specified in either the RNG-RSP or TCC encodings."
    REFERENCE
        "DOCSIS 3.0 MAC and Upper Layer Protocols Interface Specification
         CM-SP-MULPIv3.0-I19-120809, sections 8.3.3 'Dynamic Range Window' and
         C.1.5.1.9 'Dynamic Range Window'"
    ::= { cmChannelBondingUpstreamEntry 2 }

cmBondedUsDRWViolations OBJECT-TYPE
    SYNTAX      Counter32
    MAX-ACCESS  read-only
    STATUS      current
    DESCRIPTION
        "This object counts the number of RNG-RSP power adjustments made by the
         CMTS which would cause the CM to violate the constraints of the dynamic
         ranging window.

         Such adjustments (if any) will have been ignored by the CM in
         compliance with DOCSIS 3.0 requirements."
    REFERENCE
        "DOCSIS 3.0 MAC and Upper Layer Protocols Interface Specification
         CM-SP-MULPIv3.0-I19-120809, section 8.3.3.5 'Power Offset in RNG-RSP
         Causing Dynamic Range Window Violation'."
    ::= { cmChannelBondingUpstreamEntry 3 }

cmUcastDsidAllowNonZeroInitialPsn OBJECT-TYPE
    SYNTAX      TruthValue
    MAX-ACCESS  read-write
    STATUS      current
    DESCRIPTION
        "Setting this object to true(1) allows the CM to disregard the
         requirement that the packet sequence number for a newly created
         unicast resequencing DSID must begin at zero.  This allows the CM
         to recover more quickly when an invalid initial PSN is received for
         a unicast DSID.

         Note that in order to comply with DOCSIS 3.0 requirements, this
         object MUST be set to a value of false(2)."
    REFERENCE
        "DOCSIS 3.0 MAC and Upper Layer Protocols Interface Specification
         CM-SP-MULPIv3.0-I19-120809, section 8.2.3 'Sequenced Downstream
         Packets'."
    DEFVAL { false }
    ::= { cmChannelBonding 3 }

cmStartDsidLearningWhenDccRspArriveSent OBJECT-TYPE
    SYNTAX      TruthValue
    MAX-ACCESS  read-write
    STATUS      current
    DESCRIPTION
        "Setting this object to true(1) causes the CM to discard the next
         expected sequence number for all DSIDs when a DCC-RSP (arrive) message
         is sent, in case the PSNs are reset by the CMTS at this time.  This
         allows the CM to bypass the two minute out of range PSN window and
         reset the next expected sequence numbers immediately.

         Note that in order to comply with DOCSIS 3.0 requirements, this object
         MUST be set to a value of false(2)."
    REFERENCE
        "DOCSIS 3.0 MAC and Upper Layer Protocols Interface Specification
         CM-SP-MULPIv3.0-I19-120809, sections 8.2.3.1 'Downstream Sequencing'"
    DEFVAL { false }
    ::= { cmChannelBonding 4 }

cmChannelBondingCapability OBJECT-TYPE
    SYNTAX      BITS {
                downstream(0),
                upstream(1)
    }
    MAX-ACCESS  read-write
    STATUS      current
    DESCRIPTION
        "This object controls the channel bonding capability of the modem as
         advertised in the Multiple Transmit Channel Support (5.24) and
         Multiple Receive Channel Support (5.29) fields of the CM's modem
         capabilities message.

         If the downstream(0) and/or upstream(1) bits are set, then the modem
         will advertise the corresponding bonding capability accurately to the
         extent supported by the hardware.

         If either or both bits are clear, then the modem will advertise that
         the corresponding bonding capability is unsupported by using a value
         of 0 in the corresponding field."
    REFERENCE
        "DOCSIS 3.0 MAC and Upper Layer Protocols Interface Specification
         CM-SP-MULPIv3.0-I19-120809, section C.1.3.1 'Modem Capabilities
         Encoding'"
    DEFVAL { { downstream, upstream } }
    ::= { cmChannelBonding 5 }

cmDownstreamNumChannels OBJECT-TYPE
    SYNTAX      Integer32 (0..32)
    MAX-ACCESS  read-only
    STATUS      current
    DESCRIPTION
        "This object reports the number of downstream channels which are
         currently in use.  The value reported by this object corresponds to
         the number of entries in the ifTable with an ifType value of
         docsCableDownstream(128)"
    ::= { cmChannelBonding 6 }

cmUpstreamNumChannels OBJECT-TYPE
    SYNTAX      Integer32 (0..16)
    MAX-ACCESS  read-only
    STATUS      current
    DESCRIPTION
        "This object reports the number of upstream channels which are
         currently in use.  The value reported by this object corresponds to
         the number of entries in the ifTable with an ifType value of
         docsCableUpstream(129)"
    ::= { cmChannelBonding 7 }

cmUpstreamMtcMode OBJECT-TYPE
    SYNTAX      TruthValue
    MAX-ACCESS  read-only
    STATUS      current
    DESCRIPTION
        "This object reports whether the CM is currently operating in multiple
         transmit channel mode as described in the DOCSIS 3.0 MULPI
         specification.

         Note that it is possible for the CM to be operating in MTC mode even
         if only a single upstream channel is in use."
    REFERENCE
        "DOCSIS 3.0 MAC and Upper Layer Protocols Interface Specification
         CM-SP-MULPIv3.0-I19-120809, sections 8.3 'Upstream Channel Bonding'"
    ::= { cmChannelBonding 8 }


-- cmBfcEvents provides a node under which CM-specific event
-- OIDs may be defined for use in the bfcEventLogTable.

cmBfcEvents OBJECT IDENTIFIER ::= { cablemodemMgmt 4 }

-- This event satisfies Comcast requirement [REQ_E-UE-LOG-150]:
-- "The UE MUST log the name of the CM and MTA configuration file applied to
-- the device, and the timestamp of when the configuration file was applied.
-- This log MUST support up to 10 entries and be written to persistent memory."
cmConfigFileEvent OBJECT-IDENTITY
    STATUS     current
    DESCRIPTION
        "An event giving details regarding the CM config file.  At a minimum,
         this event will contain the IP address and path from which the config
         file was downloaded."
    ::= { cmBfcEvents 1 }


-- Group which implements CM spectrum analysis for devices which are capable of
-- supporting this feature

cmSpectrumAnalysis OBJECT IDENTIFIER ::= { cablemodemMgmt 5 }

cmSpectrumAnalysisMeasurementTable OBJECT-TYPE
    SYNTAX      SEQUENCE OF CmSpectrumAnalysisMeasurementEntry
    MAX-ACCESS  not-accessible
    STATUS      current
    DESCRIPTION
        "This table provides a CM downstream spectrum analysis function. Each
         measurement is a data collection event that provides the energy content
         of the signal at each frequency within a specified range.  Each row in
         the table constitutes a segment of the total measurement.

         The segments are constrained to be contiguous; that is, the start
         frequency of each segment equals the end frequency of the previous
         segment plus the bin spacing.  Thus, the concatenation of all segments
         results in a wideband spectral analysis.

         The measurement table is updated at a rate that is vendor specific. The
         measurement generally occurs prior to the point at which the received
         signal is demodulated. The measurement spectrum may or may not include
         the effects of receiver processing such as gain control, RF filtering,
         and matched filtering.

         The properties of this table are controlled by the values of the
         following objects:  cmSpectrumAnalysisFirstSegmentCenterFrequency,
         cmSpectrumAnalysisLastSegmentCenterFrequency, and
         cmSpectrumAnalysisFirstSegmentFrequencySpan.

         The value of cmSpectrumAnalysisFirstSegmentCenterFrequency and
         cmSpectrumAnalysisLastSegmentCenterFrequency control the span of the
         complete analysis operation.  The value of
         cmSpectrumAnalysisFirstSegmentFrequencySpan controls the frequency span
         analyzed by each entry in the table.

         The first instance of cmSpectrumAnalysisFrequency will have a value
         equal to the value of cmSpectrumAnalysisFirstSegmentCenterFrequency.
         Each subsequent entry will have a value of cmSpectrumAnalysisFrequency
         which is equal to the value of the previous instance incremented by the
         value of cmSpectrumAnalysisFirstSegmentFrequencySpan. The last instance
         of cmSpectrumAnalysisFrequency will have a value equal to the value of
         cmSpectrumAnalysisLastSegmentCenterFrequency."
    ::= { cmSpectrumAnalysis 1 }

cmSpectrumAnalysisMeasurementEntry OBJECT-TYPE
    SYNTAX      CmSpectrumAnalysisMeasurementEntry
    MAX-ACCESS  not-accessible
    STATUS      current
    DESCRIPTION
        "Each row in the cmSpectrumAnalysisMeasurementTable corresponds to a
         capture of spectral data across a specified segment bandwidth.

         The frequency range of each segment is divided into bins, which are a
         discrete set of evenly spaced frequencies across the band.  The width
         of each bin (resolution bandwidth) is generally equal to or slightly
         greater than the spacing between bins.  Each bin has an associated
         amplitude value in the table, which represents the amount of energy
         measured in that frequency bin."
    INDEX { cmSpectrumAnalysisFrequency }
    ::= { cmSpectrumAnalysisMeasurementTable 1 }

CmSpectrumAnalysisMeasurementEntry ::=
    SEQUENCE    {
                cmSpectrumAnalysisFrequency      Integer32,
                cmSpectrumAnalysisAmplitudeData  AmplitudeData
    }

cmSpectrumAnalysisFrequency OBJECT-TYPE
     SYNTAX      Integer32 (0..2147483647)
     MAX-ACCESS  not-accessible
     STATUS      current
     DESCRIPTION
         "This object indicates the center frequency of the spectral analysis
          segment."
     ::= { cmSpectrumAnalysisMeasurementEntry 1 }

cmSpectrumAnalysisAmplitudeData OBJECT-TYPE
     SYNTAX      AmplitudeData
     MAX-ACCESS  read-only
     STATUS      current
     DESCRIPTION
         "This object provides a list of the measured spectral amplitudes for
          the segment corresponding to the center frequency specified by the
          cmSpectrumAnalysisFrequency object.

          The frequency bins are ordered from lowest to highest frequencies
          covering the frequency span of the segment. Information about the
          center frequency, frequency span, number of bins and resolution
          bandwidth are included to provide context to the measurement point.

          Bin Amplitudes are reported in units of 0.01dB."
     ::= { cmSpectrumAnalysisMeasurementEntry 2 }

cmSpectrumAnalysisEnable OBJECT-TYPE
    SYNTAX      TruthValue
    MAX-ACCESS  read-write
    STATUS      current
    DESCRIPTION
        "This object is used to enable or disable the spectrum analyzer feature.
         By default, the feature is disabled unless explicitly enabled.

         Note that the feature may be disabled by the system under certain
         circumstances if the spectrum analyzer would affect critical services.
         In such a case, the object will return 'false' when read, and will
         reject sets to 'true' with an 'inconsistentValue' error."
    DEFVAL { false }
    ::= { cmSpectrumAnalysis 2 }

cmSpectrumAnalysisInactivityTimeout OBJECT-TYPE
    SYNTAX      Integer32 (0..86400)
    UNITS       "seconds"
    MAX-ACCESS  read-write
    STATUS      current
    DESCRIPTION
        "This object controls the length of time after the last spectrum
         analysis measurement before the feature is automatically disabled.
         If set to a value of 0, the feature will remain enabled until it is
         explicitly disabled."
    DEFVAL { 300 }
    ::= { cmSpectrumAnalysis 3 }

cmSpectrumAnalysisDiagnosticMode OBJECT-TYPE
    SYNTAX      INTEGER {
                disabled(0),
                squareWave(1),
                lockData(2)
    }
    MAX-ACCESS  read-write
    STATUS      current
    DESCRIPTION
        "This object may be used to enter a diagnostic mode of operation for the
         spectrum analyzer.  When set to disabled(0), diagnostic mode is
         disabled and the spectrum analyzer will operate normally.

         When operating in one of the diagnostic modes, no actual measurements
         will be performed.  Instead, a test pattern will be returned.

         squareWave(1): a square wave will be generated with a period of 20MHz
                        and a 50% duty cycle.

         lockData(2): actual spectrum measurement will be suspended, and data
                      returned will be that which was collected by the most
                      recent measurement."
    DEFVAL { disabled }
    ::= { cmSpectrumAnalysis 4 }

cmSpectrumAnalysisFirstSegmentCenterFrequency OBJECT-TYPE
    SYNTAX      Integer32 (0..1070000000)
    UNITS       "hertz"
    MAX-ACCESS  read-write
    STATUS      current
    DESCRIPTION
        "This object controls the center frequency of the first segment for
         the spectrum analysis measurement.

         The frequency bins for this segment lie symmetrically to the left and
         right of this center frequency.  If the number of bins in a segment is
         odd, the segment center frequency lies directly on the center bin.  If
         the number of bins in a segment is even, the segment center frequency
         lies halfway between two bins.

         Changing the value of this object may result in changes to the
         cmSpectrumAnalysisMeasurementTable, as described in the description
         field for the table.

         Note that if this object is set to an invalid value, the device may
         return an error of inconsistentValue, or may adjust the value of the
         object to the closest valid value."
    DEFVAL { 0 }
    ::= { cmSpectrumAnalysis 5 }

cmSpectrumAnalysisLastSegmentCenterFrequency OBJECT-TYPE
    SYNTAX      Integer32 (0..1070000000)
    UNITS       "hertz"
    MAX-ACCESS  read-write
    STATUS      current
    DESCRIPTION
        "This object controls the center frequency of the last segment for
         the spectrum analysis measurement.

         The frequency bins for this segment lie symmetrically to the left and
         right of this center frequency.  If the number of bins in a segment is
         odd, the segment center frequency lies directly on the center bin.  If
         the number of bins in a segment is even, the segment center frequency
         lies halfway between two bins.

         Changing the value of this object may result in changes to the
         cmSpectrumAnalysisMeasurementTable, as described in the description
         field for the table.

         Note that if this object is set to an invalid value, the device may
         return an error of inconsistentValue, or may adjust the value of the
         object to the closest valid value."
    DEFVAL { 1000000000 }
    ::= { cmSpectrumAnalysis 6 }

cmSpectrumAnalysisSegmentFrequencySpan OBJECT-TYPE
    SYNTAX      Integer32 (0 | 1000000..1070000000) -- 1MHz to 1GHz
    UNITS       "hertz"
    MAX-ACCESS  read-write
    STATUS      current
    DESCRIPTION
        "This object controls the frequency span of each segment (row) in the
         cmSpectrumAnalysisMeasurementTable.  If set to a value of 0, then a
         default span will be chosen based on the hardware capabilities of the
         device.

         Segments are contiguous from the FirstSegementCenterFrequency to the
         LastSegmentCenterFrequency and the center frequency for each successive
         segment is incremented by the SegmentFequencySpan. The number of
         segments may be calculated as

         (LastSegmentCenterFrequency - FirstSegmentCenterFrequency) / (SegmentFrequencySpan + 1)

         Each segment is represented by a row in the cmSpectrumAnalysisMeasurementTable.

         Changing the value of this object may result in changes to the
         cmSpectrumAnalysisMeasurementTable, as described in the description
         field for the table.

         Note that if this object is set to an invalid value, the device may
         return an error of inconsistentValue, or may adjust the value of the
         object to the closest valid value."
    DEFVAL { 7500000 }
    ::= { cmSpectrumAnalysis 7 }

cmSpectrumAnalysisBinsPerSegment OBJECT-TYPE
    SYNTAX      Integer32 (0 | 2..2048)
    MAX-ACCESS  read-write
    STATUS      current
    DESCRIPTION
        "This object controls the number of bins collected by the measurement
         performed for each segment (row) in the cmSpectrumAnalysisMeasurementTable.
         If set to a value of 0, then an optimal number of bins will be chosen
         based on the hardware capabilities of the device.

         Note that if this object is set to an invalid value, the device may
         return an error of inconsistentValue, or may adjust the value of the
         object to the closest valid value."
    DEFVAL { 256 }
    ::= { cmSpectrumAnalysis 8 }

cmSpectrumAnalysisWindowFunction OBJECT-TYPE
    SYNTAX      INTEGER {
                other(0),
                hann(1), -- AKA 'hanning'
                blackmanHarris(2),
                rectangular(3),
                hamming(4),
                flatTop(5),
                gaussian(6),
                chebyshev(7)
    }
    MAX-ACCESS  read-write
    STATUS      current
    DESCRIPTION
        "This attribute controls the window function which will be used when
         performing the discrete Fourier transform for the analysis.  The
         equivalent noise bandwidth for the function which is in use will be
         reported by the cmSpectrumAnalysisEquivalentNoiseBandwidth object.

         Note that all window functions may not be supported by all devices.  If
         an attempt is made to set the object to an unsupported window function,
         an error of inconsistentValue will be returned."
    REFERENCE
        "Harris, Fredric J. (Jan 1978). 'On the use of Windows for Harmonic
         Analysis with the Discrete Fourier Transform'.
         Proceedings of the IEEE 66 (1): 51-83. doi:10.1109/PROC.1978.10837"
    DEFVAL { hann }
    ::= { cmSpectrumAnalysis 9 }

cmSpectrumAnalysisEquivalentNoiseBandwidth OBJECT-TYPE
    SYNTAX      Integer32 (100..225)
    UNITS       "hundredth bins"
    MAX-ACCESS  read-write
    STATUS      current
    DESCRIPTION
        "This object allows the user to request an equivalent noise bandwidth
         for the resolution bandwidth filter used in the spectrum analysis.  This
         corresponds to the spectral width of the window function used when
         performing a discrete Fourier transform for the analysis.

         A list of equivalent noise bandwidth values for common window functions
         may be found in Table 1 of the paper identified in the reference clause
         of this object.

         The window function which corresponds to a value written to this object
         may be obtained by reading the value of cmSpectrumAnalysisWindowFunction.

         If an unsupported value is requested, the device may return an error
         of inconsistentValue, or choose the closest valid value to the one
         which is requested.  If the closest value is chosen, then a subsequent
         read of this object will return the actual value which is in use."
    REFERENCE
        "Harris, Fredric J. (Jan 1978). 'On the use of Windows for Harmonic
         Analysis with the Discrete Fourier Transform'.
         Proceedings of the IEEE 66 (1): 51-83. doi:10.1109/PROC.1978.10837"
    DEFVAL { 150 } -- hann
    ::= { cmSpectrumAnalysis 10 }

-- This spectrum analysis sub-group implements a 'reference spectrum' which
-- is measured on demand and stored to non-volatile storage.  The reference
-- spectrum (sometimes described as a 'birth certificate') may be retrieved
-- at any time, and may also be periodically compared against a current
-- spectrum measurement for the purpose of raising alarms.

cmSpectrumAnalysisReferenceSpectrum OBJECT IDENTIFIER ::= { cmSpectrumAnalysis 11 }

cmReferenceSpectrumNumSamples OBJECT-TYPE
    SYNTAX      Integer32 (0 | 512 | 1024)
    MAX-ACCESS  read-write
    STATUS      current
    DESCRIPTION
        "This object controls the number of samples which are collected when
         a reference spectrum measurement is performed.  A larger number of
         samples provides a finer resolution in the reference, at the cost of
         increased non-volatile storage requirements.

         If this object is set to a value of 0, then a subsequent set of
         cmReferenceSpectrumMeasureAndStore to 'true' will cause any existing
         reference spectrum to be cleared from non-volatile storage."
    DEFVAL { 1024 }
    ::= { cmSpectrumAnalysisReferenceSpectrum 1 }

cmReferenceSpectrumMeasurementsPerBin OBJECT-TYPE
    SYNTAX      Integer32 (1..16)
    MAX-ACCESS  read-write
    STATUS      current
    DESCRIPTION
        "This object controls the number of measurements which are performed
         and averaged for each bin during the collection of a single full
         spectrum scan.  More than one such scan may be averaged together to
         produce the resulting reference spectrum."
    DEFVAL { 4 }
    ::= { cmSpectrumAnalysisReferenceSpectrum 2 }

cmReferenceSpectrumNumAverages OBJECT-TYPE
    SYNTAX      Integer32 (1..16)
    MAX-ACCESS  read-write
    STATUS      current
    DESCRIPTION
        "This object controls the number of full spectrum scans which are
         performed and averaged together to produce the resulting reference
         spectrum."
    DEFVAL { 16 }
    ::= { cmSpectrumAnalysisReferenceSpectrum 3 }

cmReferenceSpectrumMeasureAndStore OBJECT-TYPE
    SYNTAX      TruthValue
    MAX-ACCESS  read-write
    STATUS      current
    DESCRIPTION
        "This object is used to initiate the collection of a reference spectrum.
         When set to 'true', a measurement will be performed and the resulting
         reference spectrum will be stored to non-volatile storage.

         When read, this object always returns 'false'."
    ::= { cmSpectrumAnalysisReferenceSpectrum 4 }

cmReferenceSpectrumMeasurementTable OBJECT-TYPE
    SYNTAX      SEQUENCE OF CmReferenceSpectrumMeasurementEntry
    MAX-ACCESS  not-accessible
    STATUS      current
    DESCRIPTION
        "This table represents a stored spectrum analysis reference across the
         entire spectrum.  Its format is identical to that of the
         cmSpectrumAnalysisMeasurementTable.

         The data in this table represents a snapshot of the spectrum at the
         time the data was collected.  For example, a reference spectrum might
         be collected at the time when a device is installed.

         Once collected, the data is stored to non-volatile storage and may be
         retrieved at any time to allow stored plant conditions to be compared
         to current plant conditions.

         Automatic periodic comparisons may be configured by the
         cmReferenceSpectrumComparisonThreshold and
         cmReferenceSpectrumComparisonInterval objects."
    ::= { cmSpectrumAnalysisReferenceSpectrum 5 }

cmReferenceSpectrumMeasurementEntry OBJECT-TYPE
    SYNTAX      CmReferenceSpectrumMeasurementEntry
    MAX-ACCESS  not-accessible
    STATUS      current
    DESCRIPTION
        "Each row in the cmSpectrumAnalysisMeasurementTable corresponds to a
         capture of spectral data across a specified segment bandwidth.

         The frequency range of each segment is divided into bins, which are a
         discrete set of evenly spaced frequencies across the band.  The width
         of each bin (resolution bandwidth) is generally equal to or slightly
         greater than the spacing between bins.  Each bin has an associated
         amplitude value in the table, which represents the amount of energy
         measured in that frequency bin."
    INDEX { cmReferenceSpectrumFrequency }
    ::= { cmReferenceSpectrumMeasurementTable 1 }

CmReferenceSpectrumMeasurementEntry ::=
    SEQUENCE    {
                cmReferenceSpectrumFrequency      Integer32,
                cmReferenceSpectrumAmplitudeData  AmplitudeData
    }

cmReferenceSpectrumFrequency OBJECT-TYPE
     SYNTAX      Integer32 (0..2147483647)
     MAX-ACCESS  not-accessible
     STATUS      current
     DESCRIPTION
         "This object indicates the center frequency of the spectral reference
          segment."
     ::= { cmReferenceSpectrumMeasurementEntry 1 }

cmReferenceSpectrumAmplitudeData OBJECT-TYPE
     SYNTAX      AmplitudeData
     MAX-ACCESS  read-only
     STATUS      current
     DESCRIPTION
         "This object provides a list of the measured spectral amplitudes for
          the segment corresponding to the center frequency specified by the
          cmReferenceSpectrumFrequency object.

          The frequency bins are ordered from lowest to highest frequencies
          covering the frequency span of the segment. Information about the
          center frequency, frequency span, number of bins and resolution
          bandwidth are included to provide context to the measurement point.

          Bin Amplitudes are reported in units of 0.01dB."
     ::= { cmReferenceSpectrumMeasurementEntry 2 }

cmReferenceSpectrumComparisonThreshold OBJECT-TYPE
    SYNTAX      Integer32 (0..30)
    UNITS       "dBm"
    MAX-ACCESS  read-write
    STATUS      current
    DESCRIPTION
        "This object is used to configure a threshold which will be used in
         a periodic comparison of the stored reference spectrum to current
         plant conditions.

         For each frequency band which has been configured for comparison in
         the cmReferenceSpectrumComparisonTable, if the average power for the
         band differs from the stored average power by a magnitude greater
         than the value of this object then the band will be considered to
         be out of range.

         Note that the value of this object is always non-negative, because a
         power variation in either the positive or negative direction will
         constitute the threshold being exceeded.

         A value of 0 means that no threshold is to be applied.  In this case,
         periodic measurements may still be taken but no evaluation will be
         performed.  The user may manually inspect values via the
         cmReferenceSpectrumComparisonTable."
    DEFVAL { 3 } -- +/- 3 dBm
    ::= { cmSpectrumAnalysisReferenceSpectrum 6 }

cmReferenceSpectrumComparisonInterval OBJECT-TYPE
    SYNTAX      Integer32
    UNITS       "minutes"
    MAX-ACCESS  read-write
    STATUS      current
    DESCRIPTION
        "This object is used to configure the interval at which periodic
         spectrum scans are performed and compared against the stored reference
         spectrum.

         If this object is set to a value of 0, then one scan will be performed
         immediately but no further periodic scanning will take place."
    DEFVAL { 0 }
    ::= { cmSpectrumAnalysisReferenceSpectrum 7 }

cmReferenceSpectrumComparisonTable OBJECT-TYPE
    SYNTAX      SEQUENCE OF CmReferenceSpectrumComparisonEntry
    MAX-ACCESS  not-accessible
    STATUS      current
    DESCRIPTION
        "This table defines a number of frequency bands for which composite
         power is measured and compared against a threshold in order to
         evaluate whether the band is currently within a desirable power range.

         The threshold against which the comparison is made is specified by the
         value of the cmReferenceSpectrumComparisonThreshold object."
    ::= { cmSpectrumAnalysisReferenceSpectrum 8 }

cmReferenceSpectrumComparisonEntry OBJECT-TYPE
    SYNTAX      CmReferenceSpectrumComparisonEntry
    MAX-ACCESS  not-accessible
    STATUS      current
    DESCRIPTION
        "An entry describing the number of frequency bands and threshold for
         composite power."
    INDEX { cmReferenceSpectrumCompFrequency }
    ::= { cmReferenceSpectrumComparisonTable 1 }

CmReferenceSpectrumComparisonEntry ::=
    SEQUENCE    {
                cmReferenceSpectrumCompFrequency            Integer32,
                cmReferenceSpectrumCompWidth                Integer32,
                cmReferenceSpectrumCompStoredPower          Integer32,
                cmReferenceSpectrumCompCurPower             Integer32,
                cmReferenceSpectrumCompThresholdExceeded    TruthValue,
                cmReferenceSpectrumCompStatus               RowStatus
    }

cmReferenceSpectrumCompFrequency OBJECT-TYPE
    SYNTAX      Integer32 (0..2147483647)
    UNITS       "hertz"
    MAX-ACCESS  not-accessible
    STATUS      current
    DESCRIPTION
        "Identifies the center frequency of the comparison band represented by
         this entry."
    ::= { cmReferenceSpectrumComparisonEntry 1 }

cmReferenceSpectrumCompWidth OBJECT-TYPE
    SYNTAX      Integer32
    UNITS       "hertz"
    MAX-ACCESS  read-create
    STATUS      current
    DESCRIPTION
        "Identifies the width of the comparison band represented by this entry."
    ::= { cmReferenceSpectrumComparisonEntry 2 }

cmReferenceSpectrumCompStoredPower OBJECT-TYPE
    SYNTAX      Integer32
    UNITS       "hundredth dBm"
    MAX-ACCESS  read-only
    STATUS      current
    DESCRIPTION
        "Reports the composite power for the frequency band represented by this
         entry as calculated from the stored reference spectrum data."
    ::= { cmReferenceSpectrumComparisonEntry 3 }

cmReferenceSpectrumCompCurPower OBJECT-TYPE
    SYNTAX      Integer32
    UNITS       "hundredth dBm"
    MAX-ACCESS  read-only
    STATUS      current
    DESCRIPTION
        "Reports the composite power for the frequency band represented by this
         entry as calculated from the most recently measured reference spectrum
         data."
    ::= { cmReferenceSpectrumComparisonEntry 4 }

cmReferenceSpectrumCompThresholdExceeded OBJECT-TYPE
    SYNTAX      TruthValue
    MAX-ACCESS  read-only
    STATUS      current
    DESCRIPTION
        "Indicates whether the most recently measured composite power level
         for this frequency band exceeds the comparison threshold specified by
         the value of the cmReferenceSpectrumComparisonThreshold object.  The
         value of this object reports 'true' if the threshold is exceeded, and
         'false' if the current power is within the threshold range."
    ::= { cmReferenceSpectrumComparisonEntry 5 }

cmReferenceSpectrumCompStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         cmReferenceSpectrumCompStatus column is 'notReady'.

         In particular, a newly created row cannot be made active until the
         corresponding instance of cmReferenceSpectrumCompWidth has been set.

         Only comparison bands with a status of active(1) will be measured
         and evaluated against the cmReferenceSpectrumComparisonThreshold."
    ::= { cmReferenceSpectrumComparisonEntry 6 }


cmEmbeddedDevices OBJECT IDENTIFIER ::= { cablemodemMgmt 98 }

--
-- Notifications, aka traps.
--

cmNotification OBJECT IDENTIFIER ::= { cablemodemMgmt 99 }

cmNotificationBase OBJECT IDENTIFIER ::= { cmNotification 1 }

cmDocsDevEventTrap NOTIFICATION-TYPE
    OBJECTS {
              docsDevEvLevel,
              docsDevEvId,
              docsDevEvText,
              ifPhysAddress,
              docsIfCmCmtsAddress,
              docsIfDocsisBaseCapability,
              docsIfCmStatusDocsisOperMode,
              docsIfCmStatusModulationType
            }
    STATUS current
    DESCRIPTION
        "A notification with the standard DOCSIS event log variable bindings.
         This notification may be used for vendor-specific events which do not
         have a suitable notification defined among the standard DOCSIS traps."
    ::= { cmNotificationBase 1 }

cmNotificationDocsis30 OBJECT IDENTIFIER ::= { cmNotification 3 }

cmMDDTimeoutTrap NOTIFICATION-TYPE
    OBJECTS {
              docsDevEvLevel,
              docsDevEvId,
              docsDevEvText,
              ifPhysAddress,
              docsIfCmCmtsAddress,
              docsIfDocsisBaseCapability,
              docsIfCmStatusDocsisOperMode,
              docsIfCmStatusModulationType
            }
    STATUS current
    DESCRIPTION
        "An event to report that no MDDs are being received on one or more
         of the secondary downstream channels."
    ::= { cmNotificationDocsis30 1 }

--
-- Conformance definitions
--
cmConformance      OBJECT IDENTIFIER ::= { cablemodemMgmt 100 }

--
-- Compliance Statements
--
cmCompliances  OBJECT IDENTIFIER ::= { cmConformance 1 }
cmGroups       OBJECT IDENTIFIER ::= { cmConformance 2 }

cmCompliance  MODULE-COMPLIANCE
    STATUS      current
    DESCRIPTION
        "The compliance statement for cablemodem devices."
    MODULE
    MANDATORY-GROUPS {
               cmBaseGroup,
               cmFilterGroup,
               cmChannelBondingGroup,
               cmSpectrumAnalysisGroup,
               cmNotificationGroup
    }
    ::= { cmCompliances 1 }

cmBaseGroup OBJECT-GROUP
    OBJECTS {
        cmNumLLCFiltersSupported,
        cmNumIpFiltersSupported,
        cmMiniFirewallEnable,
        cmDsdExtendedRetryEnable,
        cmCpeInterface,
        cmResetFactoryDefaults,
        cmTodRefreshInterval,
        cmDsChanInfoCodewordErrorRate,
        cmDsChanInfoMeanSquareError,
        cmDsChanInfoTuner,
        cmDsChanInfoTunerChannel,
        cmServiceQueueMaxQueueDepth,
        cmServiceQueueCurrentQueueDepth,
        cmForwardingHwAssistEnable,
        cmOverrideUcdMaxBurst,
        cmExtendedUsTxPowerCapability,
        cmIpOperMode,
        cmDocsis30NonVolEnabledFeatures,
        cmHalInterfaces
    }
    STATUS      current
    DESCRIPTION
        "A set of objects supported by all agents which implement this MIB."
    ::= { cmGroups 1 }

cmFilterGroup OBJECT-GROUP
    OBJECTS {
        cmHostIpFilterStatus,
        cmHostIpFilterStorageType,
        cmHostIpFilterMatches,
        cmHostIpFilterInterfaces,
        cmHostIpFilterDirection,
        cmHostIpFilterDestPortLow,
        cmHostIpFilterDestPortHigh
    }
    STATUS      current
    DESCRIPTION
        "A set of objects supported by agents which support CM extended
         filtering as described by this MIB."
    ::= { cmGroups 2 }

cmChannelBondingGroup OBJECT-GROUP
    OBJECTS {
        cmBondedUsDRWTop,
        cmBondedUsDRWBottom,
        cmBondedUsDRWViolations,
        cmUcastDsidAllowNonZeroInitialPsn,
        cmStartDsidLearningWhenDccRspArriveSent,
        cmChannelBondingCapability,
        cmDownstreamNumChannels,
        cmUpstreamNumChannels,
        cmUpstreamMtcMode
    }
    STATUS      current
    DESCRIPTION
        "A set of objects supported by agents for products which support channel
         bonding."
    ::= { cmGroups 3 }

cmSpectrumAnalysisGroup OBJECT-GROUP
    OBJECTS {
        cmSpectrumAnalysisAmplitudeData,
        cmSpectrumAnalysisEnable,
        cmSpectrumAnalysisInactivityTimeout,
        cmSpectrumAnalysisDiagnosticMode,
        cmSpectrumAnalysisFirstSegmentCenterFrequency,
        cmSpectrumAnalysisLastSegmentCenterFrequency,
        cmSpectrumAnalysisSegmentFrequencySpan,
        cmSpectrumAnalysisBinsPerSegment,
        cmSpectrumAnalysisWindowFunction,
        cmSpectrumAnalysisEquivalentNoiseBandwidth,
        cmReferenceSpectrumNumSamples,
        cmReferenceSpectrumMeasurementsPerBin,
        cmReferenceSpectrumNumAverages,
        cmReferenceSpectrumMeasureAndStore,
        cmReferenceSpectrumAmplitudeData,
        cmReferenceSpectrumAmplitudeData,
        cmReferenceSpectrumComparisonThreshold,
        cmReferenceSpectrumComparisonInterval,
        cmReferenceSpectrumCompWidth,
        cmReferenceSpectrumCompStoredPower,
        cmReferenceSpectrumCompCurPower,
        cmReferenceSpectrumCompThresholdExceeded,
        cmReferenceSpectrumCompStatus
    }
    STATUS      current
    DESCRIPTION
        "A set of objects supported by agents for products which support
         spectrum analysis capability."
    ::= { cmGroups 4 }

cmObsoleteGroup OBJECT-GROUP
    OBJECTS {
        cmIpProvisioningMode,
        cmChannelBondingPowerSaveStrategy
    }
    STATUS      obsolete
    DESCRIPTION
        "A set of objects which are now obsolete or deprecated"
    ::= { cmGroups 5 }

cmNotificationGroup NOTIFICATION-GROUP
    NOTIFICATIONS {
        cmDocsDevEventTrap,
        cmMDDTimeoutTrap
    }
    STATUS current
    DESCRIPTION
        "CM notifications"
    ::= { cmGroups 99 }

END
