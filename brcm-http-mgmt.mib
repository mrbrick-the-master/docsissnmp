--****************************************************************************
--
-- Copyright (c) 2004-2014 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--**************************************************************************
--    Filename: brcm-http-mgmt.mib
--    Author:   Kevin O'Neal
--    Creation Date: 24-february-2004
--
--**************************************************************************
--    Description:
--
--      private MIB for runtime BFC management
--
--**************************************************************************
--    Revision History:
--
--**************************************************************************

BRCM-HTTP-MGMT-MIB DEFINITIONS ::= BEGIN

IMPORTS
    MODULE-IDENTITY,
    OBJECT-TYPE,
    Unsigned32,
    Integer32
        FROM SNMPv2-SMI
    DisplayString
        FROM SNMPv2-TC
    cableDataMgmtBase
        FROM BRCM-CABLEDATA-MGMT-MIB;

httpMgmt MODULE-IDENTITY
    LAST-UPDATED "201401080000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to HTTP."
    REVISION      "201401080000Z"
    DESCRIPTION
            "Textual updates."
    REVISION      "201304110000Z"
    DESCRIPTION
        "Added Unsigned32 to the IMPORTS section."
    REVISION      "201209120000Z"
    DESCRIPTION
        "Added object httpWanAccessTimeout."
    REVISION      "200702050000Z"
    DESCRIPTION
        "Module description was updated."
    REVISION      "200402240000Z"
    DESCRIPTION
        "Initial version of this MIB module."
    ::= { cableDataMgmtBase 3 }

httpAdminId OBJECT-TYPE
    SYNTAX      DisplayString
    MAX-ACCESS  read-write
    STATUS      current
    DESCRIPTION
        "Controls and reflects the user name for admin level HTTP privileges."
    DEFVAL { "" }
    ::= { httpMgmt 1 }

httpAdminPassword OBJECT-TYPE
    SYNTAX      DisplayString
    MAX-ACCESS  read-write
    STATUS      current
    DESCRIPTION
        "Controls and reflects the password for admin level HTTP privileges."
    DEFVAL { "" }
    ::= { httpMgmt 2 }

httpUserId OBJECT-TYPE
    SYNTAX      DisplayString
    MAX-ACCESS  read-write
    STATUS      current
    DESCRIPTION
        "Controls and reflects the user name for user level HTTP privileges."
    DEFVAL { "" }
    ::= { httpMgmt 3 }

httpUserPassword OBJECT-TYPE
    SYNTAX      DisplayString
    MAX-ACCESS  read-write
    STATUS      current
    DESCRIPTION
        "Controls and reflects the password for user level HTTP privileges."
    DEFVAL { "" }
    ::= { httpMgmt 4 }

httpIpStackInterfaces OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which an HTTP server
         is active.  By default, the HTTP server is enabled only on the private
         IP stack interface."
    ::= { httpMgmt 5 }

httpAdvancedAccessEnabled OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which advanced
        access is allowed.  By default, advanced access is allowed only on
        remote stack interfaces."
    ::= { httpMgmt 6 }

httpPasswordOfTheDaySeed OBJECT-TYPE
    SYNTAX      DisplayString
    MAX-ACCESS  read-write
    STATUS      current
    DESCRIPTION
        "Controls and reflects the seed used to generate the password of the day."
    DEFVAL { "" }
    ::= { httpMgmt 7 }


httpLoginTimeout OBJECT-TYPE
    SYNTAX      Unsigned32
    UNITS       "seconds"
    MAX-ACCESS  read-write
    STATUS      current
    DESCRIPTION
        "Controls the timeout of the webpage login in seconds."
    DEFVAL { 0 }
    ::= { httpMgmt 8 }

httpWanAccessTimeout OBJECT-TYPE
    SYNTAX      Integer32 (0..86400)
    UNITS       "seconds"
    MAX-ACCESS  read-write
    STATUS      current
    DESCRIPTION
        "This object controls the length of time after which HTTP access
         via the WAN interface will be terminated if no HTTP activity via the
         WAN interface is detected within this period.  If set to a value of 0, 
         there will be no such timeout in effect.

         The timer begins running when the HTTP server starts.  After the number 
         of seconds specified by this object has elapsed, if no http traffic
         has been detected via the WAN interface, a filter will be created which
         drops all HTTP traffic destined to any of the device's IP addresses 
         which arrives via the WAN interface.

         If any HTTP activity via the WAN interface is detected during the 
         period of time alloted by this object, the timer will be reset.

         Setting this object to any value will cause the timer to be reset."
    DEFVAL { 0 }
    ::= { httpMgmt 9 }

END
